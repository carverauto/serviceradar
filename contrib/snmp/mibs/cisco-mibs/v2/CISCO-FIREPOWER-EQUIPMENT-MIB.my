-- *********************************************************************
-- CISCO-FIREPOWER-EQUIPMENT-MIB.my
-- 
-- MIB representation of the Cisco Firepower
-- EQUIPMENT management information model package
-- 
-- Created May 2024 by Charles Bullis
-- 
-- Copyright (c) 2005-2024 Cisco Systems, Inc. All rights reserved.
-- 
-- *********************************************************************

CISCO-FIREPOWER-EQUIPMENT-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprComputeLinkAggregationCap,
    CfprComputeMemoryUnitConstraintType,
    CfprConditionRemoteInvRslt,
    CfprConditionSeverity,
    CfprEquipmentActiveStatus,
    CfprEquipmentAdminPowerState,
    CfprEquipmentAirflowDirection,
    CfprEquipmentAppType,
    CfprEquipmentAsicType,
    CfprEquipmentBeaconLedFsmCurrentFsm,
    CfprEquipmentBeaconLedFsmStageName,
    CfprEquipmentBeaconLedFsmTaskItem,
    CfprEquipmentBeaconLedState,
    CfprEquipmentBiosUpdateMethod,
    CfprEquipmentBoardAggregationRole,
    CfprEquipmentCType,
    CfprEquipmentCardAdminState,
    CfprEquipmentChassisAdminState,
    CfprEquipmentChassisConfigProgressIndicator,
    CfprEquipmentChassisConfigState,
    CfprEquipmentChassisFsmCurrentFsm,
    CfprEquipmentChassisFsmStageName,
    CfprEquipmentChassisFsmTaskFlags,
    CfprEquipmentChassisFsmTaskItem,
    CfprEquipmentChassisId,
    CfprEquipmentChassisIssues,
    CfprEquipmentChassisPowerOperState,
    CfprEquipmentChassisStatsHistThresholded,
    CfprEquipmentChassisStatsThresholded,
    CfprEquipmentCommStatus,
    CfprEquipmentConnectionStatus,
    CfprEquipmentDiscoveryCapOperPowerRequirement,
    CfprEquipmentDiscoveryState,
    CfprEquipmentEnabledStatus,
    CfprEquipmentEthPortSpeedCap,
    CfprEquipmentFanId,
    CfprEquipmentFanModule,
    CfprEquipmentFanModuleId,
    CfprEquipmentFanModuleStatsHistThresholded,
    CfprEquipmentFanModuleStatsThresholded,
    CfprEquipmentFanModuleTray,
    CfprEquipmentFanStatsHistThresholded,
    CfprEquipmentFanStatsThresholded,
    CfprEquipmentFanTray,
    CfprEquipmentFexCapProviderRole,
    CfprEquipmentFexEnvStatsHistThresholded,
    CfprEquipmentFexEnvStatsThresholded,
    CfprEquipmentFexFsmCurrentFsm,
    CfprEquipmentFexFsmStageName,
    CfprEquipmentFexFsmTaskItem,
    CfprEquipmentFexId,
    CfprEquipmentFexPowerSummaryHistThresholded,
    CfprEquipmentFexPowerSummaryThresholded,
    CfprEquipmentFexPsuInputStatsHistThresholded,
    CfprEquipmentFexPsuInputStatsThresholded,
    CfprEquipmentHealthLedState,
    CfprEquipmentIOCardBaseFsmCurrentFsm,
    CfprEquipmentIOCardBaseFsmStageName,
    CfprEquipmentIOCardBaseFsmTaskFlags,
    CfprEquipmentIOCardBaseFsmTaskItem,
    CfprEquipmentIOCardFsmCurrentFsm,
    CfprEquipmentIOCardFsmStageName,
    CfprEquipmentIOCardFsmTaskItem,
    CfprEquipmentIOCardId,
    CfprEquipmentIOCardIssues,
    CfprEquipmentIOCardStatsHistThresholded,
    CfprEquipmentIOCardStatsThresholded,
    CfprEquipmentInternalFanType,
    CfprEquipmentIsSupported,
    CfprEquipmentLedColor,
    CfprEquipmentLedLocatorState,
    CfprEquipmentLedOperState,
    CfprEquipmentLocatorLedFsmCurrentFsm,
    CfprEquipmentLocatorLedFsmStageName,
    CfprEquipmentLocatorLedFsmTaskItem,
    CfprEquipmentMediaType,
    CfprEquipmentMemoryUnitDiscoveryModifierAction,
    CfprEquipmentMethod,
    CfprEquipmentNetworkElementFanStatsHistThresholded,
    CfprEquipmentNetworkElementFanStatsThresholded,
    CfprEquipmentOperability,
    CfprEquipmentOwnership,
    CfprEquipmentPOSTRecoverability,
    CfprEquipmentPasswordState,
    CfprEquipmentPictureType,
    CfprEquipmentPortAttribute,
    CfprEquipmentPowerCapDefProfileMethod,
    CfprEquipmentPowerState,
    CfprEquipmentPresence,
    CfprEquipmentPsuEnvPsuType,
    CfprEquipmentPsuId,
    CfprEquipmentPsuInputSrc,
    CfprEquipmentPsuInputStatsHistThresholded,
    CfprEquipmentPsuInputStatsThresholded,
    CfprEquipmentPsuOutputStatsHistThresholded,
    CfprEquipmentPsuOutputStatsThresholded,
    CfprEquipmentPsuStateQualifier,
    CfprEquipmentPsuStatsHistThresholded,
    CfprEquipmentPsuStatsThresholded,
    CfprEquipmentPsuType,
    CfprEquipmentPsuVoltageType,
    CfprEquipmentRackUnitFanStatsHistThresholded,
    CfprEquipmentRackUnitFanStatsThresholded,
    CfprEquipmentRackUnitPsuStatsHistThresholded,
    CfprEquipmentRackUnitPsuStatsThresholded,
    CfprEquipmentRemovalConditions,
    CfprEquipmentResetOn,
    CfprEquipmentSecureBios,
    CfprEquipmentSensorThresholdStatus,
    CfprEquipmentShutdownAction,
    CfprEquipmentSlotArrayLocation,
    CfprEquipmentSlotArrayOrientation,
    CfprEquipmentSlotArraySelector,
    CfprEquipmentSlotSpanOrientation,
    CfprEquipmentStorageMethod,
    CfprEquipmentSwitchIOCardFsmCurrentFsm,
    CfprEquipmentSwitchIOCardFsmStageName,
    CfprEquipmentSwitchIOCardId,
    CfprEquipmentTpmConfigSupport,
    CfprEquipmentTpmType,
    CfprEquipmentUnifiedPortAlgorithm,
    CfprEquipmentUuidFeatureCapUuidSupportMode,
    CfprEquipmentXcvrId,
    CfprEquipmentXcvrStatus,
    CfprEquipmentXcvrType,
    CfprFsmCompletion,
    CfprFsmFlags,
    CfprFsmFsmStageStatus,
    CfprLicenseState,
    CfprMgmtUpgradeStatus,
    CfprNetworkSide,
    CfprNetworkSwitchId,
    CfprPolicyPolicyOwner,
    CfprPortEthSpeed,
    CfprPortGroupType,
    CfprPortSpeed,
    CfprStorageControllerForm,
    CfprStorageLocalDiskMode,
    CfprStorageTechnology
        FROM CISCO-FIREPOWER-TC-MIB;

cfprEquipmentObjects MODULE-IDENTITY
    LAST-UPDATED    "202405160000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        EQUIPMENT management information model package"
    ::= { ciscoFirepowerMIBObjects 20 }

cfprEquipmentAdaptorConnDefTable OBJECT-TYPE
    SYNTAX           SEQUENCE OF CfprEquipmentAdaptorConnDefEntry
    MAX-ACCESS       not-accessible
    STATUS           current
    DESCRIPTION
        "Cisco Firepower equipment:AdaptorConnDef managed object table"
    ::= { cfprEquipmentObjects 1 }

cfprEquipmentAdaptorConnDefEntry OBJECT-TYPE
    SYNTAX           CfprEquipmentAdaptorConnDefEntry
    MAX-ACCESS       not-accessible
    STATUS           current
    DESCRIPTION
        "Entry for the cfprEquipmentAdaptorConnDefTable table."
    INDEX { cfprEquipmentAdaptorConnDefInstanceId }
    ::= { cfprEquipmentAdaptorConnDefTable 1 }

CfprEquipmentAdaptorConnDefEntry ::= SEQUENCE {
    cfprEquipmentAdaptorConnDefInstanceId                            CfprManagedObjectId,
    cfprEquipmentAdaptorConnDefDn                                    CfprManagedObjectDn,
    cfprEquipmentAdaptorConnDefRn                                    SnmpAdminString,
    cfprEquipmentAdaptorConnDefAdaptorEp                             Gauge32,
    cfprEquipmentAdaptorConnDefDescr                                 SnmpAdminString,
    cfprEquipmentAdaptorConnDefIntId                                 SnmpAdminString,
    cfprEquipmentAdaptorConnDefIomEp                                 Gauge32,
    cfprEquipmentAdaptorConnDefName                                  SnmpAdminString,
    cfprEquipmentAdaptorConnDefPolicyLevel                           Gauge32,
    cfprEquipmentAdaptorConnDefPolicyOwner                           CfprPolicyPolicyOwner
}

cfprEquipmentAdaptorConnDefInstanceId OBJECT-TYPE
    SYNTAX       CfprManagedObjectId
    MAX-ACCESS   not-accessible
    STATUS       current
    DESCRIPTION
        "Instance identifier of the managed object."
    ::= { cfprEquipmentAdaptorConnDefEntry 1 }

cfprEquipmentAdaptorConnDefDn OBJECT-TYPE
    SYNTAX       CfprManagedObjectDn
    MAX-ACCESS   read-only
    STATUS       current
    DESCRIPTION
        "Cisco Firepower equipment:AdaptorConnDef:dn managed
        object property"
    ::= { cfprEquipmentAdaptorConnDefEntry 2 }

cfprEquipmentAdaptorConnDefRn OBJECT-TYPE
    SYNTAX       SnmpAdminString
    MAX-ACCESS   read-only
    STATUS       current
    DESCRIPTION
        "Cisco Firepower equipment:AdaptorConnDef:rn managed
        object property"
    ::= { cfprEquipmentAdaptorConnDefEntry 3 }

cfprEquipmentAdaptorConnDefAdaptorEp OBJECT-TYPE
    SYNTAX       Gauge32
    MAX-ACCESS   read-only
    STATUS       current
    DESCRIPTION
        "Cisco Firepower equipment:AdaptorConnDef:adaptorEp
        managed object property"
    ::= { cfprEquipmentAdaptorConnDefEntry 4 }

cfprEquipmentAdaptorConnDefDescr OBJECT-TYPE
    SYNTAX       SnmpAdminString
    MAX-ACCESS   read-only
    STATUS       current
    DESCRIPTION
        "Cisco Firepower equipment:AdaptorConnDef:descr
        managed object property"
    ::= { cfprEquipmentAdaptorConnDefEntry 5 }

cfprEquipmentAdaptorConnDefIntId OBJECT-TYPE
    SYNTAX       SnmpAdminString
    MAX-ACCESS   read-only
    STATUS       current
    DESCRIPTION
        "Cisco Firepower equipment:AdaptorConnDef:intId
        managed object property"
    ::= { cfprEquipmentAdaptorConnDefEntry 6 }

cfprEquipmentAdaptorConnDefIomEp OBJECT-TYPE
    SYNTAX       Gauge32
    MAX-ACCESS   read-only
    STATUS       current
    DESCRIPTION
        "Cisco Firepower equipment:AdaptorConnDef:iomEp
        managed object property"
    ::= { cfprEquipmentAdaptorConnDefEntry 7 }

cfprEquipmentAdaptorConnDefName OBJECT-TYPE
    SYNTAX       SnmpAdminString
    MAX-ACCESS   read-only
    STATUS       current
    DESCRIPTION
        "Cisco Firepower equipment:AdaptorConnDef:name
        managed object property"
    ::= { cfprEquipmentAdaptorConnDefEntry 8 }

cfprEquipmentAdaptorConnDefPolicyLevel OBJECT-TYPE
    SYNTAX       Gauge32
    MAX-ACCESS   read-only
    STATUS       current
    DESCRIPTION
        "Cisco Firepower equipment:AdaptorConnDef:policyLevel
        managed object property"
    ::= { cfprEquipmentAdaptorConnDefEntry 9 }

cfprEquipmentAdaptorConnDefPolicyOwner OBJECT-TYPE
    SYNTAX       CfprPolicyPolicyOwner
    MAX-ACCESS   read-only
    STATUS       current
    DESCRIPTION
        "Cisco Firepower equipment:AdaptorConnDef:policyOwner
        managed object property"
    ::= { cfprEquipmentAdaptorConnDefEntry 10 }

cfprEquipmentAdaptorDefTable OBJECT-TYPE
    SYNTAX           SEQUENCE OF CfprEquipmentAdaptorDefEntry
    MAX-ACCESS       not-accessible
    STATUS           current
    DESCRIPTION
        "Cisco Firepower equipment:AdaptorDef managed object table"
    ::= { cfprEquipmentObjects 2 }

cfprEquipmentAdaptorDefEntry OBJECT-TYPE
    SYNTAX           CfprEquipmentAdaptorDefEntry
    MAX-ACCESS       not-accessible
    STATUS           current
    DESCRIPTION
        "Entry for the cfprEquipmentAdaptorDefTable table."
    INDEX { cfprEquipmentAdaptorDefInstanceId }
    ::= { cfprEquipmentAdaptorDefTable 1 }

CfprEquipmentAdaptorDefEntry ::= SEQUENCE {
    cfprEquipmentAdaptorDefInstanceId                                CfprManagedObjectId,
    cfprEquipmentAdaptorDefDn                                        CfprManagedObjectDn,
    cfprEquipmentAdaptorDefRn                                        SnmpAdminString,
    cfprEquipmentAdaptorDefDescr                                     SnmpAdminString,
    cfprEquipmentAdaptorDefEthernetPortSpeed                         Unsigned64,
    cfprEquipmentAdaptorDefFibreChannelPortSpeed                     Unsigned64,
    cfprEquipmentAdaptorDefIntId                                     SnmpAdminString,
    cfprEquipmentAdaptorDefName                                      SnmpAdminString,
    cfprEquipmentAdaptorDefPolicyLevel                               Gauge32,
    cfprEquipmentAdaptorDefPolicyOwner                               CfprPolicyPolicyOwner
}

cfprEquipmentAdaptorDefInstanceId OBJECT-TYPE
    SYNTAX       CfprManagedObjectId
    MAX-ACCESS   not-accessible
    STATUS       current
    DESCRIPTION
        "Instance identifier of the managed object."
    ::= { cfprEquipmentAdaptorDefEntry 1 }

cfprEquipmentAdaptorDefDn OBJECT-TYPE
    SYNTAX       CfprManagedObjectDn
    MAX-ACCESS   read-only
    STATUS       current
    DESCRIPTION
        "Cisco Firepower equipment:AdaptorDef:dn managed object property"
    ::= { cfprEquipmentAdaptorDefEntry 2 }

cfprEquipmentAdaptorDefRn OBJECT-TYPE
    SYNTAX       SnmpAdminString
    MAX-ACCESS   read-only
    STATUS       current
    DESCRIPTION
        "Cisco Firepower equipment:AdaptorDef:rn managed object property"
    ::= { cfprEquipmentAdaptorDefEntry 3 }

cfprEquipmentAdaptorDefDescr OBJECT-TYPE
    SYNTAX       SnmpAdminString
    MAX-ACCESS   read-only
    STATUS       current
    DESCRIPTION
        "Cisco Firepower equipment:AdaptorDef:descr managed
        object property"
    ::= { cfprEquipmentAdaptorDefEntry 4 }

cfprEquipmentAdaptorDefEthernetPortSpeed OBJECT-TYPE
    SYNTAX       Unsigned64
    MAX-ACCESS   read-only
    STATUS       current
    DESCRIPTION
        "Cisco Firepower equipment:AdaptorDef:ethernetPortSpeed
        managed object property"
    ::= { cfprEquipmentAdaptorDefEntry 5 }

cfprEquipmentAdaptorDefFibreChannelPortSpeed OBJECT-TYPE
    SYNTAX       Unsigned64
    MAX-ACCESS   read-only
    STATUS       current
    DESCRIPTION
        "Cisco Firepower equipment:AdaptorDef:fibreChannelPortSpeed
        managed object property"
    ::= { cfprEquipmentAdaptorDefEntry 6 }

cfprEquipmentAdaptorDefIntId OBJECT-TYPE
    SYNTAX       SnmpAdminString
    MAX-ACCESS   read-only
    STATUS       current
    DESCRIPTION
        "Cisco Firepower equipment:AdaptorDef:intId managed
        object property"
    ::= { cfprEquipmentAdaptorDefEntry 7 }

cfprEquipmentAdaptorDefName OBJECT-TYPE
    SYNTAX       SnmpAdminString
    MAX-ACCESS   read-only
    STATUS       current
    DESCRIPTION
        "Cisco Firepower equipment:AdaptorDef:name managed
        object property"
    ::= { cfprEquipmentAdaptorDefEntry 8 }

cfprEquipmentAdaptorDefPolicyLevel OBJECT-TYPE
    SYNTAX       Gauge32
    MAX-ACCESS   read-only
    STATUS       current
    DESCRIPTION
        "Cisco Firepower equipment:AdaptorDef:policyLevel
        managed object property"
    ::= { cfprEquipmentAdaptorDefEntry 9 }

cfprEquipmentAdaptorDefPolicyOwner OBJECT-TYPE
    SYNTAX       CfprPolicyPolicyOwner
    MAX-ACCESS   read-only
    STATUS       current
    DESCRIPTION
        "Cisco Firepower equipment:AdaptorDef:policyOwner
        managed object property"
    ::= { cfprEquipmentAdaptorDefEntry 10 }

cfprEquipmentAdvancedBootOrderTable OBJECT-TYPE
    SYNTAX           SEQUENCE OF CfprEquipmentAdvancedBootOrderEntry
    MAX-ACCESS       not-accessible
    STATUS           current
    DESCRIPTION
        "Cisco Firepower equipment:AdvancedBootOrder managed object table"
    ::= { cfprEquipmentObjects 3 }

cfprEquipmentAdvancedBootOrderEntry OBJECT-TYPE
    SYNTAX           CfprEquipmentAdvancedBootOrderEntry
    MAX-ACCESS       not-accessible
    STATUS           current
    DESCRIPTION
        "Entry for the cfprEquipmentAdvancedBootOrderTable table."
    INDEX { cfprEquipmentAdvancedBootOrderInstanceId }
    ::= { cfprEquipmentAdvancedBootOrderTable 1 }

CfprEquipmentAdvancedBootOrderEntry ::= SEQUENCE {
    cfprEquipmentAdvancedBootOrderInstanceId                         CfprManagedObjectId,
    cfprEquipmentAdvancedBootOrderDn                                 CfprManagedObjectDn,
    cfprEquipmentAdvancedBootOrderRn                                 SnmpAdminString,
    cfprEquipmentAdvancedBootOrderDescr                              SnmpAdminString,
    cfprEquipmentAdvancedBootOrderIntId                              SnmpAdminString,
    cfprEquipmentAdvancedBootOrderIsSupported                        TruthValue,
    cfprEquipmentAdvancedBootOrderMinBiosVersion                     SnmpAdminString,
    cfprEquipmentAdvancedBootOrderMinCimcVersion                     SnmpAdminString,
    cfprEquipmentAdvancedBootOrderName                               SnmpAdminString,
    cfprEquipmentAdvancedBootOrderPolicyLevel                        Gauge32,
    cfprEquipmentAdvancedBootOrderPolicyOwner                        CfprPolicyPolicyOwner
}

cfprEquipmentAdvancedBootOrderInstanceId OBJECT-TYPE
    SYNTAX       CfprManagedObjectId
    MAX-ACCESS   not-accessible
    STATUS       current
    DESCRIPTION
        "Instance identifier of the managed object."
    ::= { cfprEquipmentAdvancedBootOrderEntry 1 }

cfprEquipmentAdvancedBootOrderDn OBJECT-TYPE
    SYNTAX       CfprManagedObjectDn
    MAX-ACCESS   read-only
    STATUS       current
    DESCRIPTION
        "Cisco Firepower equipment:AdvancedBootOrder:dn
        managed object property"
    ::= { cfprEquipmentAdvancedBootOrderEntry 2 }

cfprEquipmentAdvancedBootOrderRn OBJECT-TYPE
    SYNTAX       SnmpAdminString
    MAX-ACCESS   read-only
    STATUS       current
    DESCRIPTION
        "Cisco Firepower equipment:AdvancedBootOrder:rn
        managed object property"
    ::= { cfprEquipmentAdvancedBootOrderEntry 3 }

cfprEquipmentAdvancedBootOrderDescr OBJECT-TYPE
    SYNTAX       SnmpAdminString
    MAX-ACCESS   read-only
    STATUS       current
    DESCRIPTION
        "Cisco Firepower equipment:AdvancedBootOrder:descr
        managed object property"
    ::= { cfprEquipmentAdvancedBootOrderEntry 4 }

cfprEquipmentAdvancedBootOrderIntId OBJECT-TYPE
    SYNTAX       SnmpAdminString
    MAX-ACCESS   read-only
    STATUS       current
    DESCRIPTION
        "Cisco Firepower equipment:AdvancedBootOrder:intId
        managed object property"
    ::= { cfprEquipmentAdvancedBootOrderEntry 5 }

cfprEquipmentAdvancedBootOrderIsSupported OBJECT-TYPE
    SYNTAX       TruthValue
    MAX-ACCESS   read-only
    STATUS       current
    DESCRIPTION
        "Cisco Firepower equipment:AdvancedBootOrder:isSupported
        managed object property"
    ::= { cfprEquipmentAdvancedBootOrderEntry 6 }

cfprEquipmentAdvancedBootOrderMinBiosVersion OBJECT-TYPE
    SYNTAX       SnmpAdminString
    MAX-ACCESS   read-only
    STATUS       current
    DESCRIPTION
        "Cisco Firepower equipment:AdvancedBootOrder:minBiosVersion
        managed object property"
    ::= { cfprEquipmentAdvancedBootOrderEntry 7 }

cfprEquipmentAdvancedBootOrderMinCimcVersion OBJECT-TYPE
    SYNTAX       SnmpAdminString
    MAX-ACCESS   read-only
    STATUS       current
    DESCRIPTION
        "Cisco Firepower equipment:AdvancedBootOrder:minCimcVersion
        managed object property"
    ::= { cfprEquipmentAdvancedBootOrderEntry 8 }

cfprEquipmentAdvancedBootOrderName OBJECT-TYPE
    SYNTAX       SnmpAdminString
    MAX-ACCESS   read-only
    STATUS       current
    DESCRIPTION
        "Cisco Firepower equipment:AdvancedBootOrder:name
        managed object property"
    ::= { cfprEquipmentAdvancedBootOrderEntry 9 }

cfprEquipmentAdvancedBootOrderPolicyLevel OBJECT-TYPE
    SYNTAX       Gauge32
    MAX-ACCESS   read-only
    STATUS       current
    DESCRIPTION
        "Cisco Firepower equipment:AdvancedBootOrder:policyLevel
        managed object property"
    ::= { cfprEquipmentAdvancedBootOrderEntry 10 }

cfprEquipmentAdvancedBootOrderPolicyOwner OBJECT-TYPE
    SYNTAX       CfprPolicyPolicyOwner
    MAX-ACCESS   read-only
    STATUS       current
    DESCRIPTION
        "Cisco Firepower equipment:AdvancedBootOrder:policyOwner
        managed object property"
    ::= { cfprEquipmentAdvancedBootOrderEntry 11 }

cfprEquipmentBaseBoardCapProviderTable OBJECT-TYPE
    SYNTAX           SEQUENCE OF CfprEquipmentBaseBoardCapProviderEntry
    MAX-ACCESS       not-accessible
    STATUS           current
    DESCRIPTION
        "Cisco Firepower equipment:BaseBoardCapProvider
        managed object table"
    ::= { cfprEquipmentObjects 4 }

cfprEquipmentBaseBoardCapProviderEntry OBJECT-TYPE
    SYNTAX           CfprEquipmentBaseBoardCapProviderEntry
    MAX-ACCESS       not-accessible
    STATUS           current
    DESCRIPTION
        "Entry for the cfprEquipmentBaseBoardCapProviderTable table."
    INDEX { cfprEquipmentBaseBoardCapProviderInstanceId }
    ::= { cfprEquipmentBaseBoardCapProviderTable 1 }

CfprEquipmentBaseBoardCapProviderEntry ::= SEQUENCE {
    cfprEquipmentBaseBoardCapProviderInstanceId                      CfprManagedObjectId,
    cfprEquipmentBaseBoardCapProviderDn                              CfprManagedObjectDn,
    cfprEquipmentBaseBoardCapProviderRn                              SnmpAdminString,
    cfprEquipmentBaseBoardCapProviderDeleted                         TruthValue,
    cfprEquipmentBaseBoardCapProviderDeprecated                      TruthValue,
    cfprEquipmentBaseBoardCapProviderElementLoadFailures             Gauge32,
    cfprEquipmentBaseBoardCapProviderElementsLoaded                  Gauge32,
    cfprEquipmentBaseBoardCapProviderGencount                        Gauge32,
    cfprEquipmentBaseBoardCapProviderLoadErrors                      Gauge32,
    cfprEquipmentBaseBoardCapProviderLoadWarnings                    Gauge32,
    cfprEquipmentBaseBoardCapProviderMgmtPlaneVer                    SnmpAdminString,
    cfprEquipmentBaseBoardCapProviderModel                           SnmpAdminString,
    cfprEquipmentBaseBoardCapProviderPromCardType                    Gauge32,
    cfprEquipmentBaseBoardCapProviderRevision                        SnmpAdminString,
    cfprEquipmentBaseBoardCapProviderVendor                          SnmpAdminString
}

cfprEquipmentBaseBoardCapProviderInstanceId OBJECT-TYPE
    SYNTAX       CfprManagedObjectId
    MAX-ACCESS   not-accessible
    STATUS       current
    DESCRIPTION
        "Instance identifier of the managed object."
    ::= { cfprEquipmentBaseBoardCapProviderEntry 1 }

cfprEquipmentBaseBoardCapProviderDn OBJECT-TYPE
    SYNTAX       CfprManagedObjectDn
    MAX-ACCESS   read-only
    STATUS       current
    DESCRIPTION
        "Cisco Firepower equipment:BaseBoardCapProvider:dn
        managed object property"
    ::= { cfprEquipmentBaseBoardCapProviderEntry 2 }

cfprEquipmentBaseBoardCapProviderRn OBJECT-TYPE
    SYNTAX       SnmpAdminString
    MAX-ACCESS   read-only
    STATUS       current
    DESCRIPTION
        "Cisco Firepower equipment:BaseBoardCapProvider:rn
        managed object property"
    ::= { cfprEquipmentBaseBoardCapProviderEntry 3 }

cfprEquipmentBaseBoardCapProviderDeleted OBJECT-TYPE
    SYNTAX       TruthValue
    MAX-ACCESS   read-only
    STATUS       current
    DESCRIPTION
        "Cisco Firepower equipment:BaseBoardCapProvider:deleted
        managed object property"
    ::= { cfprEquipmentBaseBoardCapProviderEntry 4 }

cfprEquipmentBaseBoardCapProviderDeprecated OBJECT-TYPE
    SYNTAX       TruthValue
    MAX-ACCESS   read-only
    STATUS       current
    DESCRIPTION
        "Cisco Firepower equipment:BaseBoardCapProvider:deprecated
        managed object property"
    ::= { cfprEquipmentBaseBoardCapProviderEntry 5 }

cfprEquipmentBaseBoardCapProviderElementLoadFailures OBJECT-TYPE
    SYNTAX       Gauge32
    MAX-ACCESS   read-only
    STATUS       current
    DESCRIPTION
        "Cisco Firepower equipment:BaseBoardCapProvider:elementLoadFailure
        s managed object property"
    ::= { cfprEquipmentBaseBoardCapProviderEntry 6 }

cfprEquipmentBaseBoardCapProviderElementsLoaded OBJECT-TYPE
    SYNTAX       Gauge32
    MAX-ACCESS   read-only
    STATUS       current
    DESCRIPTION
        "Cisco Firepower equipment:BaseBoardCapProvider:elementsLoaded
        managed object property"
    ::= { cfprEquipmentBaseBoardCapProviderEntry 7 }

cfprEquipmentBaseBoardCapProviderGencount OBJECT-TYPE
    SYNTAX       Gauge32
    MAX-ACCESS   read-only
    STATUS       current
    DESCRIPTION
        "Cisco Firepower equipment:BaseBoardCapProvider:gencount
        managed object property"
    ::= { cfprEquipmentBaseBoardCapProviderEntry 8 }

cfprEquipmentBaseBoardCapProviderLoadErrors OBJECT-TYPE
    SYNTAX       Gauge32
    MAX-ACCESS   read-only
    STATUS       current
    DESCRIPTION
        "Cisco Firepower equipment:BaseBoardCapProvider:loadErrors
        managed object property"
    ::= { cfprEquipmentBaseBoardCapProviderEntry 9 }

cfprEquipmentBaseBoardCapProviderLoadWarnings OBJECT-TYPE
    SYNTAX       Gauge32
    MAX-ACCESS   read-only
    STATUS       current
    DESCRIPTION
        "Cisco Firepower equipment:BaseBoardCapProvider:loadWarnings
        managed object property"
    ::= { cfprEquipmentBaseBoardCapProviderEntry 10 }

cfprEquipmentBaseBoardCapProviderMgmtPlaneVer OBJECT-TYPE
    SYNTAX       SnmpAdminString
    MAX-ACCESS   read-only
    STATUS       current
    DESCRIPTION
        "Cisco Firepower equipment:BaseBoardCapProvider:mgmtPlaneVer
        managed object property"
    ::= { cfprEquipmentBaseBoardCapProviderEntry 11 }

cfprEquipmentBaseBoardCapProviderModel OBJECT-TYPE
    SYNTAX       SnmpAdminString
    MAX-ACCESS   read-only
    STATUS       current
    DESCRIPTION
        "Cisco Firepower equipment:BaseBoardCapProvider:model
        managed object property"
    ::= { cfprEquipmentBaseBoardCapProviderEntry 12 }

cfprEquipmentBaseBoardCapProviderPromCardType OBJECT-TYPE
    SYNTAX       Gauge32
    MAX-ACCESS   read-only
    STATUS       current
    DESCRIPTION
        "Cisco Firepower equipment:BaseBoardCapProvider:promCardType
        managed object property"
    ::= { cfprEquipmentBaseBoardCapProviderEntry 13 }

cfprEquipmentBaseBoardCapProviderRevision OBJECT-TYPE
    SYNTAX       SnmpAdminString
    MAX-ACCESS   read-only
    STATUS       current
    DESCRIPTION
        "Cisco Firepower equipment:BaseBoardCapProvider:revision
        managed object property"
    ::= { cfprEquipmentBaseBoardCapProviderEntry 14 }

cfprEquipmentBaseBoardCapProviderVendor OBJECT-TYPE
    SYNTAX       SnmpAdminString
    MAX-ACCESS   read-only
    STATUS       current
    DESCRIPTION
        "Cisco Firepower equipment:BaseBoardCapProvider:vendor
        managed object property"
    ::= { cfprEquipmentBaseBoardCapProviderEntry 15 }

cfprEquipmentBeaconCapProviderTable OBJECT-TYPE
    SYNTAX           SEQUENCE OF CfprEquipmentBeaconCapProviderEntry
    MAX-ACCESS       not-accessible
    STATUS           current
    DESCRIPTION
        "Cisco Firepower equipment:BeaconCapProvider managed object table"
    ::= { cfprEquipmentObjects 5 }

cfprEquipmentBeaconCapProviderEntry OBJECT-TYPE
    SYNTAX           CfprEquipmentBeaconCapProviderEntry
    MAX-ACCESS       not-accessible
    STATUS           current
    DESCRIPTION
        "Entry for the cfprEquipmentBeaconCapProviderTable table."
    INDEX { cfprEquipmentBeaconCapProviderInstanceId }
    ::= { cfprEquipmentBeaconCapProviderTable 1 }

CfprEquipmentBeaconCapProviderEntry ::= SEQUENCE {
    cfprEquipmentBeaconCapProviderInstanceId                         CfprManagedObjectId,
    cfprEquipmentBeaconCapProviderDn                                 CfprManagedObjectDn,
    cfprEquipmentBeaconCapProviderRn                                 SnmpAdminString,
    cfprEquipmentBeaconCapProviderDescr                              SnmpAdminString,
    cfprEquipmentBeaconCapProviderIntId                              SnmpAdminString,
    cfprEquipmentBeaconCapProviderName                               SnmpAdminString,
    cfprEquipmentBeaconCapProviderPolicyLevel                        Gauge32,
    cfprEquipmentBeaconCapProviderPolicyOwner                        CfprPolicyPolicyOwner,
    cfprEquipmentBeaconCapProviderPortModeBeacon                     TruthValue
}

cfprEquipmentBeaconCapProviderInstanceId OBJECT-TYPE
    SYNTAX       CfprManagedObjectId
    MAX-ACCESS   not-accessible
    STATUS       current
    DESCRIPTION
        "Instance identifier of the managed object."
    ::= { cfprEquipmentBeaconCapProviderEntry 1 }

cfprEquipmentBeaconCapProviderDn OBJECT-TYPE
    SYNTAX       CfprManagedObjectDn
    MAX-ACCESS   read-only
    STATUS       current
    DESCRIPTION
        "Cisco Firepower equipment:BeaconCapProvider:dn
        managed object property"
    ::= { cfprEquipmentBeaconCapProviderEntry 2 }

cfprEquipmentBeaconCapProviderRn OBJECT-TYPE
    SYNTAX       SnmpAdminString
    MAX-ACCESS   read-only
    STATUS       current
    DESCRIPTION
        "Cisco Firepower equipment:BeaconCapProvider:rn
        managed object property"
    ::= { cfprEquipmentBeaconCapProviderEntry 3 }

cfprEquipmentBeaconCapProviderDescr OBJECT-TYPE
    SYNTAX       SnmpAdminString
    MAX-ACCESS   read-only
    STATUS       current
    DESCRIPTION
        "Cisco Firepower equipment:BeaconCapProvider:descr
        managed object property"
    ::= { cfprEquipmentBeaconCapProviderEntry 4 }

cfprEquipmentBeaconCapProviderIntId OBJECT-TYPE
    SYNTAX       SnmpAdminString
    MAX-ACCESS   read-only
    STATUS       current
    DESCRIPTION
        "Cisco Firepower equipment:BeaconCapProvider:intId
        managed object property"
    ::= { cfprEquipmentBeaconCapProviderEntry 5 }

cfprEquipmentBeaconCapProviderName OBJECT-TYPE
    SYNTAX       SnmpAdminString
    MAX-ACCESS   read-only
    STATUS       current
    DESCRIPTION
        "Cisco Firepower equipment:BeaconCapProvider:name
        managed object property"
    ::= { cfprEquipmentBeaconCapProviderEntry 6 }

cfprEquipmentBeaconCapProviderPolicyLevel OBJECT-TYPE
    SYNTAX       Gauge32
    MAX-ACCESS   read-only
    STATUS       current
    DESCRIPTION
        "Cisco Firepower equipment:BeaconCapProvider:policyLevel
        managed object property"
    ::= { cfprEquipmentBeaconCapProviderEntry 7 }

cfprEquipmentBeaconCapProviderPolicyOwner OBJECT-TYPE
    SYNTAX       CfprPolicyPolicyOwner
    MAX-ACCESS   read-only
    STATUS       current
    DESCRIPTION
        "Cisco Firepower equipment:BeaconCapProvider:policyOwner
        managed object property"
    ::= { cfprEquipmentBeaconCapProviderEntry 8 }

cfprEquipmentBeaconCapProviderPortModeBeacon OBJECT-TYPE
    SYNTAX       TruthValue
    MAX-ACCESS   read-only
    STATUS       current
    DESCRIPTION
        "Cisco Firepower equipment:BeaconCapProvider:portModeBeacon
        managed object property"
    ::= { cfprEquipmentBeaconCapProviderEntry 9 }

cfprEquipmentBeaconLedTable OBJECT-TYPE
    SYNTAX           SEQUENCE OF CfprEquipmentBeaconLedEntry
    MAX-ACCESS       not-accessible
    STATUS           current
    DESCRIPTION
        "Cisco Firepower equipment:BeaconLed managed object table"
    ::= { cfprEquipmentObjects 6 }

cfprEquipmentBeaconLedEntry OBJECT-TYPE
    SYNTAX           CfprEquipmentBeaconLedEntry
    MAX-ACCESS       not-accessible
    STATUS           current
    DESCRIPTION
        "Entry for the cfprEquipmentBeaconLedTable table."
    INDEX { cfprEquipmentBeaconLedInstanceId }
    ::= { cfprEquipmentBeaconLedTable 1 }

CfprEquipmentBeaconLedEntry ::= SEQUENCE {
    cfprEquipmentBeaconLedInstanceId                                 CfprManagedObjectId,
    cfprEquipmentBeaconLedDn                                         CfprManagedObjectDn,
    cfprEquipmentBeaconLedRn                                         SnmpAdminString,
    cfprEquipmentBeaconLedAdminState                                 CfprEquipmentBeaconLedState,
    cfprEquipmentBeaconLedColor                                      CfprEquipmentLedColor,
    cfprEquipmentBeaconLedFsmDescr                                   SnmpAdminString,
    cfprEquipmentBeaconLedFsmPrev                                    SnmpAdminString,
    cfprEquipmentBeaconLedFsmProgr                                   Gauge32,
    cfprEquipmentBeaconLedFsmRmtInvErrCode                           Gauge32,
    cfprEquipmentBeaconLedFsmRmtInvErrDescr                          SnmpAdminString,
    cfprEquipmentBeaconLedFsmRmtInvRslt                              CfprConditionRemoteInvRslt,
    cfprEquipmentBeaconLedFsmStageDescr                              SnmpAdminString,
    cfprEquipmentBeaconLedFsmStamp                                   DateAndTime,
    cfprEquipmentBeaconLedFsmStatus                                  SnmpAdminString,
    cfprEquipmentBeaconLedFsmTry                                     Gauge32,
    cfprEquipmentBeaconLedId                                         Gauge32,
    cfprEquipmentBeaconLedName                                       SnmpAdminString,
    cfprEquipmentBeaconLedOperState                                  CfprEquipmentLedOperState
}

cfprEquipmentBeaconLedInstanceId OBJECT-TYPE
    SYNTAX       CfprManagedObjectId
    MAX-ACCESS   not-accessible
    STATUS       current
    DESCRIPTION
        "Instance identifier of the managed object."
    ::= { cfprEquipmentBeaconLedEntry 1 }

cfprEquipmentBeaconLedDn OBJECT-TYPE
    SYNTAX       CfprManagedObjectDn
    MAX-ACCESS   read-only
    STATUS       current
    DESCRIPTION
        "Cisco Firepower equipment:BeaconLed:dn managed object property"
    ::= { cfprEquipmentBeaconLedEntry 2 }

cfprEquipmentBeaconLedRn OBJECT-TYPE
    SYNTAX       SnmpAdminString
    MAX-ACCESS   read-only
    STATUS       current
    DESCRIPTION
        "Cisco Firepower equipment:BeaconLed:rn managed object property"
    ::= { cfprEquipmentBeaconLedEntry 3 }

cfprEquipmentBeaconLedAdminState OBJECT-TYPE
    SYNTAX       CfprEquipmentBeaconLedState
    MAX-ACCESS   read-only
    STATUS       current
    DESCRIPTION
        "Cisco Firepower equipment:BeaconLed:adminState
        managed object property"
    ::= { cfprEquipmentBeaconLedEntry 4 }

cfprEquipmentBeaconLedColor OBJECT-TYPE
    SYNTAX       CfprEquipmentLedColor
    MAX-ACCESS   read-only
    STATUS       current
    DESCRIPTION
        "Cisco Firepower equipment:BeaconLed:color managed
        object property"
    ::= { cfprEquipmentBeaconLedEntry 5 }

cfprEquipmentBeaconLedFsmDescr OBJECT-TYPE
    SYNTAX       SnmpAdminString
    MAX-ACCESS   read-only
    STATUS       current
    DESCRIPTION
        "Cisco Firepower equipment:BeaconLed:fsmDescr managed
        object property"
    ::= { cfprEquipmentBeaconLedEntry 6 }

cfprEquipmentBeaconLedFsmPrev OBJECT-TYPE
    SYNTAX       SnmpAdminString
    MAX-ACCESS   read-only
    STATUS       current
    DESCRIPTION
        "Cisco Firepower equipment:BeaconLed:fsmPrev managed
        object property"
    ::= { cfprEquipmentBeaconLedEntry 7 }

cfprEquipmentBeaconLedFsmProgr OBJECT-TYPE
    SYNTAX       Gauge32
    MAX-ACCESS   read-only
    STATUS       current
    DESCRIPTION
        "Cisco Firepower equipment:BeaconLed:fsmProgr managed
        object property"
    ::= { cfprEquipmentBeaconLedEntry 8 }

cfprEquipmentBeaconLedFsmRmtInvErrCode OBJECT-TYPE
    SYNTAX       Gauge32
    MAX-ACCESS   read-only
    STATUS       current
    DESCRIPTION
        "Cisco Firepower equipment:BeaconLed:fsmRmtInvErrCode
        managed object property"
    ::= { cfprEquipmentBeaconLedEntry 9 }

cfprEquipmentBeaconLedFsmRmtInvErrDescr OBJECT-TYPE
    SYNTAX       SnmpAdminString
    MAX-ACCESS   read-only
    STATUS       current
    DESCRIPTION
        "Cisco Firepower equipment:BeaconLed:fsmRmtInvErrDescr
        managed object property"
    ::= { cfprEquipmentBeaconLedEntry 10 }

cfprEquipmentBeaconLedFsmRmtInvRslt OBJECT-TYPE
    SYNTAX       CfprConditionRemoteInvRslt
    MAX-ACCESS   read-only
    STATUS       current
    DESCRIPTION
        "Cisco Firepower equipment:BeaconLed:fsmRmtInvRslt
        managed object property"
    ::= { cfprEquipmentBeaconLedEntry 11 }

cfprEquipmentBeaconLedFsmStageDescr OBJECT-TYPE
    SYNTAX       SnmpAdminString
    MAX-ACCESS   read-only
    STATUS       current
    DESCRIPTION
        "Cisco Firepower equipment:BeaconLed:fsmStageDescr
        managed object property"
    ::= { cfprEquipmentBeaconLedEntry 12 }

cfprEquipmentBeaconLedFsmStamp OBJECT-TYPE
    SYNTAX       DateAndTime
    MAX-ACCESS   read-only
    STATUS       current
    DESCRIPTION
        "Cisco Firepower equipment:BeaconLed:fsmStamp managed
        object property"
    ::= { cfprEquipmentBeaconLedEntry 13 }

cfprEquipmentBeaconLedFsmStatus OBJECT-TYPE
    SYNTAX       SnmpAdminString
    MAX-ACCESS   read-only
    STATUS       current
    DESCRIPTION
        "Cisco Firepower equipment:BeaconLed:fsmStatus
        managed object property"
    ::= { cfprEquipmentBeaconLedEntry 14 }

cfprEquipmentBeaconLedFsmTry OBJECT-TYPE
    SYNTAX       Gauge32
    MAX-ACCESS   read-only
    STATUS       current
    DESCRIPTION
        "Cisco Firepower equipment:BeaconLed:fsmTry managed
        object property"
    ::= { cfprEquipmentBeaconLedEntry 15 }

cfprEquipmentBeaconLedId OBJECT-TYPE
    SYNTAX       Gauge32
    MAX-ACCESS   read-only
    STATUS       current
    DESCRIPTION
        "Cisco Firepower equipment:BeaconLed:id managed object property"
    ::= { cfprEquipmentBeaconLedEntry 16 }

cfprEquipmentBeaconLedName OBJECT-TYPE
    SYNTAX       SnmpAdminString
    MAX-ACCESS   read-only
    STATUS       current
    DESCRIPTION
        "Cisco Firepower equipment:BeaconLed:name managed object property"
    ::= { cfprEquipmentBeaconLedEntry 17 }

cfprEquipmentBeaconLedOperState OBJECT-TYPE
    SYNTAX       CfprEquipmentLedOperState
    MAX-ACCESS   read-only
    STATUS       current
    DESCRIPTION
        "Cisco Firepower equipment:BeaconLed:operState
        managed object property"
    ::= { cfprEquipmentBeaconLedEntry 18 }

cfprEquipmentBeaconLedFsmTable OBJECT-TYPE
    SYNTAX           SEQUENCE OF CfprEquipmentBeaconLedFsmEntry
    MAX-ACCESS       not-accessible
    STATUS           current
    DESCRIPTION
        "Cisco Firepower equipment:BeaconLedFsm managed object table"
    ::= { cfprEquipmentObjects 7 }

cfprEquipmentBeaconLedFsmEntry OBJECT-TYPE
    SYNTAX           CfprEquipmentBeaconLedFsmEntry
    MAX-ACCESS       not-accessible
    STATUS           current
    DESCRIPTION
        "Entry for the cfprEquipmentBeaconLedFsmTable table."
    INDEX { cfprEquipmentBeaconLedFsmInstanceId }
    ::= { cfprEquipmentBeaconLedFsmTable 1 }

CfprEquipmentBeaconLedFsmEntry ::= SEQUENCE {
    cfprEquipmentBeaconLedFsmInstanceId                              CfprManagedObjectId,
    cfprEquipmentBeaconLedFsmDn                                      CfprManagedObjectDn,
    cfprEquipmentBeaconLedFsmRn                                      SnmpAdminString,
    cfprEquipmentBeaconLedFsmCompletionTime                          DateAndTime,
    cfprEquipmentBeaconLedFsmCurrentFsm                              CfprEquipmentBeaconLedFsmCurrentFsm,
    cfprEquipmentBeaconLedFsmDescrData                               SnmpAdminString,
    cfprEquipmentBeaconLedFsmFsmStatus                               CfprFsmFsmStageStatus,
    cfprEquipmentBeaconLedFsmProgress                                Gauge32,
    cfprEquipmentBeaconLedFsmRmtErrCode                              Gauge32,
    cfprEquipmentBeaconLedFsmRmtErrDescr                             SnmpAdminString,
    cfprEquipmentBeaconLedFsmRmtRslt                                 CfprConditionRemoteInvRslt
}

cfprEquipmentBeaconLedFsmInstanceId OBJECT-TYPE
    SYNTAX       CfprManagedObjectId
    MAX-ACCESS   not-accessible
    STATUS       current
    DESCRIPTION
        "Instance identifier of the managed object."
    ::= { cfprEquipmentBeaconLedFsmEntry 1 }

cfprEquipmentBeaconLedFsmDn OBJECT-TYPE
    SYNTAX       CfprManagedObjectDn
    MAX-ACCESS   read-only
    STATUS       current
    DESCRIPTION
        "Cisco Firepower equipment:BeaconLedFsm:dn managed
        object property"
    ::= { cfprEquipmentBeaconLedFsmEntry 2 }

cfprEquipmentBeaconLedFsmRn OBJECT-TYPE
    SYNTAX       SnmpAdminString
    MAX-ACCESS   read-only
    STATUS       current
    DESCRIPTION
        "Cisco Firepower equipment:BeaconLedFsm:rn managed
        object property"
    ::= { cfprEquipmentBeaconLedFsmEntry 3 }

cfprEquipmentBeaconLedFsmCompletionTime OBJECT-TYPE
    SYNTAX       DateAndTime
    MAX-ACCESS   read-only
    STATUS       current
    DESCRIPTION
        "Cisco Firepower equipment:BeaconLedFsm:completionTime
        managed object property"
    ::= { cfprEquipmentBeaconLedFsmEntry 4 }

cfprEquipmentBeaconLedFsmCurrentFsm OBJECT-TYPE
    SYNTAX       CfprEquipmentBeaconLedFsmCurrentFsm
    MAX-ACCESS   read-only
    STATUS       current
    DESCRIPTION
        "Cisco Firepower equipment:BeaconLedFsm:currentFsm
        managed object property"
    ::= { cfprEquipmentBeaconLedFsmEntry 5 }

cfprEquipmentBeaconLedFsmDescrData OBJECT-TYPE
    SYNTAX       SnmpAdminString
    MAX-ACCESS   read-only
    STATUS       current
    DESCRIPTION
        "Cisco Firepower equipment:BeaconLedFsm:descr managed
        object property"
    ::= { cfprEquipmentBeaconLedFsmEntry 6 }

cfprEquipmentBeaconLedFsmFsmStatus OBJECT-TYPE
    SYNTAX       CfprFsmFsmStageStatus
    MAX-ACCESS   read-only
    STATUS       current
    DESCRIPTION
        "Cisco Firepower equipment:BeaconLedFsm:fsmStatus
        managed object property"
    ::= { cfprEquipmentBeaconLedFsmEntry 7 }

cfprEquipmentBeaconLedFsmProgress OBJECT-TYPE
    SYNTAX       Gauge32
    MAX-ACCESS   read-only
    STATUS       current
    DESCRIPTION
        "Cisco Firepower equipment:BeaconLedFsm:progress
        managed object property"
    ::= { cfprEquipmentBeaconLedFsmEntry 8 }

cfprEquipmentBeaconLedFsmRmtErrCode OBJECT-TYPE
    SYNTAX       Gauge32
    MAX-ACCESS   read-only
    STATUS       current
    DESCRIPTION
        "Cisco Firepower equipment:BeaconLedFsm:rmtErrCode
        managed object property"
    ::= { cfprEquipmentBeaconLedFsmEntry 9 }

cfprEquipmentBeaconLedFsmRmtErrDescr OBJECT-TYPE
    SYNTAX       SnmpAdminString
    MAX-ACCESS   read-only
    STATUS       current
    DESCRIPTION
        "Cisco Firepower equipment:BeaconLedFsm:rmtErrDescr
        managed object property"
    ::= { cfprEquipmentBeaconLedFsmEntry 10 }

cfprEquipmentBeaconLedFsmRmtRslt OBJECT-TYPE
    SYNTAX       CfprConditionRemoteInvRslt
    MAX-ACCESS   read-only
    STATUS       current
    DESCRIPTION
        "Cisco Firepower equipment:BeaconLedFsm:rmtRslt
        managed object property"
    ::= { cfprEquipmentBeaconLedFsmEntry 11 }

cfprEquipmentBeaconLedFsmStageTable OBJECT-TYPE
    SYNTAX           SEQUENCE OF CfprEquipmentBeaconLedFsmStageEntry
    MAX-ACCESS       not-accessible
    STATUS           current
    DESCRIPTION
        "Cisco Firepower equipment:BeaconLedFsmStage managed object table"
    ::= { cfprEquipmentObjects 8 }

cfprEquipmentBeaconLedFsmStageEntry OBJECT-TYPE
    SYNTAX           CfprEquipmentBeaconLedFsmStageEntry
    MAX-ACCESS       not-accessible
    STATUS           current
    DESCRIPTION
        "Entry for the cfprEquipmentBeaconLedFsmStageTable table."
    INDEX { cfprEquipmentBeaconLedFsmStageInstanceId }
    ::= { cfprEquipmentBeaconLedFsmStageTable 1 }

CfprEquipmentBeaconLedFsmStageEntry ::= SEQUENCE {
    cfprEquipmentBeaconLedFsmStageInstanceId                         CfprManagedObjectId,
    cfprEquipmentBeaconLedFsmStageDn                                 CfprManagedObjectDn,
    cfprEquipmentBeaconLedFsmStageRn                                 SnmpAdminString,
    cfprEquipmentBeaconLedFsmStageDescrData                          SnmpAdminString,
    cfprEquipmentBeaconLedFsmStageLastUpdateTime                     DateAndTime,
    cfprEquipmentBeaconLedFsmStageName                               CfprEquipmentBeaconLedFsmStageName,
    cfprEquipmentBeaconLedFsmStageOrder                              Gauge32,
    cfprEquipmentBeaconLedFsmStageRetry                              Gauge32,
    cfprEquipmentBeaconLedFsmStageStageStatus                        CfprFsmFsmStageStatus
}

cfprEquipmentBeaconLedFsmStageInstanceId OBJECT-TYPE
    SYNTAX       CfprManagedObjectId
    MAX-ACCESS   not-accessible
    STATUS       current
    DESCRIPTION
        "Instance identifier of the managed object."
    ::= { cfprEquipmentBeaconLedFsmStageEntry 1 }

cfprEquipmentBeaconLedFsmStageDn OBJECT-TYPE
    SYNTAX       CfprManagedObjectDn
    MAX-ACCESS   read-only
    STATUS       current
    DESCRIPTION
        "Cisco Firepower equipment:BeaconLedFsmStage:dn
        managed object property"
    ::= { cfprEquipmentBeaconLedFsmStageEntry 2 }

cfprEquipmentBeaconLedFsmStageRn OBJECT-TYPE
    SYNTAX       SnmpAdminString
    MAX-ACCESS   read-only
    STATUS       current
    DESCRIPTION
        "Cisco Firepower equipment:BeaconLedFsmStage:rn
        managed object property"
    ::= { cfprEquipmentBeaconLedFsmStageEntry 3 }

cfprEquipmentBeaconLedFsmStageDescrData OBJECT-TYPE
    SYNTAX       SnmpAdminString
    MAX-ACCESS   read-only
    STATUS       current
    DESCRIPTION
        "Cisco Firepower equipment:BeaconLedFsmStage:descr
        managed object property"
    ::= { cfprEquipmentBeaconLedFsmStageEntry 4 }

cfprEquipmentBeaconLedFsmStageLastUpdateTime OBJECT-TYPE
    SYNTAX       DateAndTime
    MAX-ACCESS   read-only
    STATUS       current
    DESCRIPTION
        "Cisco Firepower equipment:BeaconLedFsmStage:lastUpdateTime
        managed object property"
    ::= { cfprEquipmentBeaconLedFsmStageEntry 5 }

cfprEquipmentBeaconLedFsmStageName OBJECT-TYPE
    SYNTAX       CfprEquipmentBeaconLedFsmStageName
    MAX-ACCESS   read-only
    STATUS       current
    DESCRIPTION
        "Cisco Firepower equipment:BeaconLedFsmStage:name
        managed object property"
    ::= { cfprEquipmentBeaconLedFsmStageEntry 6 }

cfprEquipmentBeaconLedFsmStageOrder OBJECT-TYPE
    SYNTAX       Gauge32
    MAX-ACCESS   read-only
    STATUS       current
    DESCRIPTION
        "Cisco Firepower equipment:BeaconLedFsmStage:order
        managed object property"
    ::= { cfprEquipmentBeaconLedFsmStageEntry 7 }

cfprEquipmentBeaconLedFsmStageRetry OBJECT-TYPE
    SYNTAX       Gauge32
    MAX-ACCESS   read-only
    STATUS       current
    DESCRIPTION
        "Cisco Firepower equipment:BeaconLedFsmStage:retry
        managed object property"
    ::= { cfprEquipmentBeaconLedFsmStageEntry 8 }

cfprEquipmentBeaconLedFsmStageStageStatus OBJECT-TYPE
    SYNTAX       CfprFsmFsmStageStatus
    MAX-ACCESS   read-only
    STATUS       current
    DESCRIPTION
        "Cisco Firepower equipment:BeaconLedFsmStage:stageStatus
        managed object property"
    ::= { cfprEquipmentBeaconLedFsmStageEntry 9 }

cfprEquipmentBeaconLedFsmTaskTable OBJECT-TYPE
    SYNTAX           SEQUENCE OF CfprEquipmentBeaconLedFsmTaskEntry
    MAX-ACCESS       not-accessible
    STATUS           current
    DESCRIPTION
        "Cisco Firepower equipment:BeaconLedFsmTask managed object table"
    ::= { cfprEquipmentObjects 9 }

cfprEquipmentBeaconLedFsmTaskEntry OBJECT-TYPE
    SYNTAX           CfprEquipmentBeaconLedFsmTaskEntry
    MAX-ACCESS       not-accessible
    STATUS           current
    DESCRIPTION
        "Entry for the cfprEquipmentBeaconLedFsmTaskTable table."
    INDEX { cfprEquipmentBeaconLedFsmTaskInstanceId }
    ::= { cfprEquipmentBeaconLedFsmTaskTable 1 }

CfprEquipmentBeaconLedFsmTaskEntry ::= SEQUENCE {
    cfprEquipmentBeaconLedFsmTaskInstanceId                          CfprManagedObjectId,
    cfprEquipmentBeaconLedFsmTaskDn                                  CfprManagedObjectDn,
    cfprEquipmentBeaconLedFsmTaskRn                                  SnmpAdminString,
    cfprEquipmentBeaconLedFsmTaskCompletion                          CfprFsmCompletion,
    cfprEquipmentBeaconLedFsmTaskFlags                               CfprFsmFlags,
    cfprEquipmentBeaconLedFsmTaskItem                                CfprEquipmentBeaconLedFsmTaskItem,
    cfprEquipmentBeaconLedFsmTaskSeqId                               Gauge32
}

cfprEquipmentBeaconLedFsmTaskInstanceId OBJECT-TYPE
    SYNTAX       CfprManagedObjectId
    MAX-ACCESS   not-accessible
    STATUS       current
    DESCRIPTION
        "Instance identifier of the managed object."
    ::= { cfprEquipmentBeaconLedFsmTaskEntry 1 }

cfprEquipmentBeaconLedFsmTaskDn OBJECT-TYPE
    SYNTAX       CfprManagedObjectDn
    MAX-ACCESS   read-only
    STATUS       current
    DESCRIPTION
        "Cisco Firepower equipment:BeaconLedFsmTask:dn
        managed object property"
    ::= { cfprEquipmentBeaconLedFsmTaskEntry 2 }

cfprEquipmentBeaconLedFsmTaskRn OBJECT-TYPE
    SYNTAX       SnmpAdminString
    MAX-ACCESS   read-only
    STATUS       current
    DESCRIPTION
        "Cisco Firepower equipment:BeaconLedFsmTask:rn
        managed object property"
    ::= { cfprEquipmentBeaconLedFsmTaskEntry 3 }

cfprEquipmentBeaconLedFsmTaskCompletion OBJECT-TYPE
    SYNTAX       CfprFsmCompletion
    MAX-ACCESS   read-only
    STATUS       current
    DESCRIPTION
        "Cisco Firepower equipment:BeaconLedFsmTask:completion
        managed object property"
    ::= { cfprEquipmentBeaconLedFsmTaskEntry 4 }

cfprEquipmentBeaconLedFsmTaskFlags OBJECT-TYPE
    SYNTAX       CfprFsmFlags
    MAX-ACCESS   read-only
    STATUS       current
    DESCRIPTION
        "Cisco Firepower equipment:BeaconLedFsmTask:flags
        managed object property"
    ::= { cfprEquipmentBeaconLedFsmTaskEntry 5 }

cfprEquipmentBeaconLedFsmTaskItem OBJECT-TYPE
    SYNTAX       CfprEquipmentBeaconLedFsmTaskItem
    MAX-ACCESS   read-only
    STATUS       current
    DESCRIPTION
        "Cisco Firepower equipment:BeaconLedFsmTask:item
        managed object property"
    ::= { cfprEquipmentBeaconLedFsmTaskEntry 6 }

cfprEquipmentBeaconLedFsmTaskSeqId OBJECT-TYPE
    SYNTAX       Gauge32
    MAX-ACCESS   read-only
    STATUS       current
    DESCRIPTION
        "Cisco Firepower equipment:BeaconLedFsmTask:seqId
        managed object property"
    ::= { cfprEquipmentBeaconLedFsmTaskEntry 7 }

cfprEquipmentBiosDefTable OBJECT-TYPE
    SYNTAX           SEQUENCE OF CfprEquipmentBiosDefEntry
    MAX-ACCESS       not-accessible
    STATUS           current
    DESCRIPTION
        "Cisco Firepower equipment:BiosDef managed object table"
    ::= { cfprEquipmentObjects 10 }

cfprEquipmentBiosDefEntry OBJECT-TYPE
    SYNTAX           CfprEquipmentBiosDefEntry
    MAX-ACCESS       not-accessible
    STATUS           current
    DESCRIPTION
        "Entry for the cfprEquipmentBiosDefTable table."
    INDEX { cfprEquipmentBiosDefInstanceId }
    ::= { cfprEquipmentBiosDefTable 1 }

CfprEquipmentBiosDefEntry ::= SEQUENCE {
    cfprEquipmentBiosDefInstanceId                                   CfprManagedObjectId,
    cfprEquipmentBiosDefDn                                           CfprManagedObjectDn,
    cfprEquipmentBiosDefRn                                           SnmpAdminString,
    cfprEquipmentBiosDefDescr                                        SnmpAdminString,
    cfprEquipmentBiosDefIntId                                        SnmpAdminString,
    cfprEquipmentBiosDefName                                         SnmpAdminString,
    cfprEquipmentBiosDefPolicyLevel                                  Gauge32,
    cfprEquipmentBiosDefPolicyOwner                                  CfprPolicyPolicyOwner,
    cfprEquipmentBiosDefResetOn                                      CfprEquipmentResetOn,
    cfprEquipmentBiosDefSecureBios                                   CfprEquipmentSecureBios,
    cfprEquipmentBiosDefStorageMethod                                CfprEquipmentStorageMethod,
    cfprEquipmentBiosDefUpdateMethod                                 CfprEquipmentBiosUpdateMethod,
    cfprEquipmentBiosDefTpmConfigSupport                             CfprEquipmentTpmConfigSupport
}

cfprEquipmentBiosDefInstanceId OBJECT-TYPE
    SYNTAX       CfprManagedObjectId
    MAX-ACCESS   not-accessible
    STATUS       current
    DESCRIPTION
        "Instance identifier of the managed object."
    ::= { cfprEquipmentBiosDefEntry 1 }

cfprEquipmentBiosDefDn OBJECT-TYPE
    SYNTAX       CfprManagedObjectDn
    MAX-ACCESS   read-only
    STATUS       current
    DESCRIPTION
        "Cisco Firepower equipment:BiosDef:dn managed object property"
    ::= { cfprEquipmentBiosDefEntry 2 }

cfprEquipmentBiosDefRn OBJECT-TYPE
    SYNTAX       SnmpAdminString
    MAX-ACCESS   read-only
    STATUS       current
    DESCRIPTION
        "Cisco Firepower equipment:BiosDef:rn managed object property"
    ::= { cfprEquipmentBiosDefEntry 3 }

cfprEquipmentBiosDefDescr OBJECT-TYPE
    SYNTAX       SnmpAdminString
    MAX-ACCESS   read-only
    STATUS       current
    DESCRIPTION
        "Cisco Firepower equipment:BiosDef:descr managed object property"
    ::= { cfprEquipmentBiosDefEntry 4 }

cfprEquipmentBiosDefIntId OBJECT-TYPE
    SYNTAX       SnmpAdminString
    MAX-ACCESS   read-only
    STATUS       current
    DESCRIPTION
        "Cisco Firepower equipment:BiosDef:intId managed object property"
    ::= { cfprEquipmentBiosDefEntry 5 }

cfprEquipmentBiosDefName OBJECT-TYPE
    SYNTAX       SnmpAdminString
    MAX-ACCESS   read-only
    STATUS       current
    DESCRIPTION
        "Cisco Firepower equipment:BiosDef:name managed object property"
    ::= { cfprEquipmentBiosDefEntry 6 }

cfprEquipmentBiosDefPolicyLevel OBJECT-TYPE
    SYNTAX       Gauge32
    MAX-ACCESS   read-only
    STATUS       current
    DESCRIPTION
        "Cisco Firepower equipment:BiosDef:policyLevel
        managed object property"
    ::= { cfprEquipmentBiosDefEntry 7 }

cfprEquipmentBiosDefPolicyOwner OBJECT-TYPE
    SYNTAX       CfprPolicyPolicyOwner
    MAX-ACCESS   read-only
    STATUS       current
    DESCRIPTION
        "Cisco Firepower equipment:BiosDef:policyOwner
        managed object property"
    ::= { cfprEquipmentBiosDefEntry 8 }

cfprEquipmentBiosDefResetOn OBJECT-TYPE
    SYNTAX       CfprEquipmentResetOn
    MAX-ACCESS   read-only
    STATUS       current
    DESCRIPTION
        "Cisco Firepower equipment:BiosDef:resetOn managed
        object property"
    ::= { cfprEquipmentBiosDefEntry 9 }

cfprEquipmentBiosDefSecureBios OBJECT-TYPE
    SYNTAX       CfprEquipmentSecureBios
    MAX-ACCESS   read-only
    STATUS       current
    DESCRIPTION
        "Cisco Firepower equipment:BiosDef:secureBios managed
        object property"
    ::= { cfprEquipmentBiosDefEntry 10 }

cfprEquipmentBiosDefStorageMethod OBJECT-TYPE
    SYNTAX       CfprEquipmentStorageMethod
    MAX-ACCESS   read-only
    STATUS       current
    DESCRIPTION
        "Cisco Firepower equipment:BiosDef:storageMethod
        managed object property"
    ::= { cfprEquipmentBiosDefEntry 11 }

cfprEquipmentBiosDefUpdateMethod OBJECT-TYPE
    SYNTAX       CfprEquipmentBiosUpdateMethod
    MAX-ACCESS   read-only
    STATUS       current
    DESCRIPTION
        "Cisco Firepower equipment:BiosDef:updateMethod
        managed object property"
    ::= { cfprEquipmentBiosDefEntry 12 }

cfprEquipmentBiosDefTpmConfigSupport OBJECT-TYPE
    SYNTAX       CfprEquipmentTpmConfigSupport
    MAX-ACCESS   read-only
    STATUS       current
    DESCRIPTION
        "Cisco Firepower equipment:BiosDef:tpmConfigSupport
        managed object property"
    ::= { cfprEquipmentBiosDefEntry 13 }

cfprEquipmentBladeAGLibraryTable OBJECT-TYPE
    SYNTAX           SEQUENCE OF CfprEquipmentBladeAGLibraryEntry
    MAX-ACCESS       not-accessible
    STATUS           current
    DESCRIPTION
        "Cisco Firepower equipment:BladeAGLibrary managed object table"
    ::= { cfprEquipmentObjects 11 }

cfprEquipmentBladeAGLibraryEntry OBJECT-TYPE
    SYNTAX           CfprEquipmentBladeAGLibraryEntry
    MAX-ACCESS       not-accessible
    STATUS           current
    DESCRIPTION
        "Entry for the cfprEquipmentBladeAGLibraryTable table."
    INDEX { cfprEquipmentBladeAGLibraryInstanceId }
    ::= { cfprEquipmentBladeAGLibraryTable 1 }

CfprEquipmentBladeAGLibraryEntry ::= SEQUENCE {
    cfprEquipmentBladeAGLibraryInstanceId                            CfprManagedObjectId,
    cfprEquipmentBladeAGLibraryDn                                    CfprManagedObjectDn,
    cfprEquipmentBladeAGLibraryRn                                    SnmpAdminString,
    cfprEquipmentBladeAGLibraryDescr                                 SnmpAdminString,
    cfprEquipmentBladeAGLibraryIntId                                 SnmpAdminString,
    cfprEquipmentBladeAGLibraryName                                  SnmpAdminString,
    cfprEquipmentBladeAGLibraryPolicyLevel                           Gauge32,
    cfprEquipmentBladeAGLibraryPolicyOwner                           CfprPolicyPolicyOwner
}

cfprEquipmentBladeAGLibraryInstanceId OBJECT-TYPE
    SYNTAX       CfprManagedObjectId
    MAX-ACCESS   not-accessible
    STATUS       current
    DESCRIPTION
        "Instance identifier of the managed object."
    ::= { cfprEquipmentBladeAGLibraryEntry 1 }

cfprEquipmentBladeAGLibraryDn OBJECT-TYPE
    SYNTAX       CfprManagedObjectDn
    MAX-ACCESS   read-only
    STATUS       current
    DESCRIPTION
        "Cisco Firepower equipment:BladeAGLibrary:dn managed
        object property"
    ::= { cfprEquipmentBladeAGLibraryEntry 2 }

cfprEquipmentBladeAGLibraryRn OBJECT-TYPE
    SYNTAX       SnmpAdminString
    MAX-ACCESS   read-only
    STATUS       current
    DESCRIPTION
        "Cisco Firepower equipment:BladeAGLibrary:rn managed
        object property"
    ::= { cfprEquipmentBladeAGLibraryEntry 3 }

cfprEquipmentBladeAGLibraryDescr OBJECT-TYPE
    SYNTAX       SnmpAdminString
    MAX-ACCESS   read-only
    STATUS       current
    DESCRIPTION
        "Cisco Firepower equipment:BladeAGLibrary:descr
        managed object property"
    ::= { cfprEquipmentBladeAGLibraryEntry 4 }

cfprEquipmentBladeAGLibraryIntId OBJECT-TYPE
    SYNTAX       SnmpAdminString
    MAX-ACCESS   read-only
    STATUS       current
    DESCRIPTION
        "Cisco Firepower equipment:BladeAGLibrary:intId
        managed object property"
    ::= { cfprEquipmentBladeAGLibraryEntry 5 }

cfprEquipmentBladeAGLibraryName OBJECT-TYPE
    SYNTAX       SnmpAdminString
    MAX-ACCESS   read-only
    STATUS       current
    DESCRIPTION
        "Cisco Firepower equipment:BladeAGLibrary:name
        managed object property"
    ::= { cfprEquipmentBladeAGLibraryEntry 6 }

cfprEquipmentBladeAGLibraryPolicyLevel OBJECT-TYPE
    SYNTAX       Gauge32
    MAX-ACCESS   read-only
    STATUS       current
    DESCRIPTION
        "Cisco Firepower equipment:BladeAGLibrary:policyLevel
        managed object property"
    ::= { cfprEquipmentBladeAGLibraryEntry 7 }

cfprEquipmentBladeAGLibraryPolicyOwner OBJECT-TYPE
    SYNTAX       CfprPolicyPolicyOwner
    MAX-ACCESS   read-only
    STATUS       current
    DESCRIPTION
        "Cisco Firepower equipment:BladeAGLibrary:policyOwner
        managed object property"
    ::= { cfprEquipmentBladeAGLibraryEntry 8 }

cfprEquipmentBladeAggregationCapRefTable OBJECT-TYPE
    SYNTAX           SEQUENCE OF CfprEquipmentBladeAggregationCapRefEntry
    MAX-ACCESS       not-accessible
    STATUS           current
    DESCRIPTION
        "Cisco Firepower equipment:BladeAggregationCapRef
        managed object table"
    ::= { cfprEquipmentObjects 12 }

cfprEquipmentBladeAggregationCapRefEntry OBJECT-TYPE
    SYNTAX           CfprEquipmentBladeAggregationCapRefEntry
    MAX-ACCESS       not-accessible
    STATUS           current
    DESCRIPTION
        "Entry for the cfprEquipmentBladeAggregationCapRefTable table."
    INDEX { cfprEquipmentBladeAggregationCapRefInstanceId }
    ::= { cfprEquipmentBladeAggregationCapRefTable 1 }

CfprEquipmentBladeAggregationCapRefEntry ::= SEQUENCE {
    cfprEquipmentBladeAggregationCapRefInstanceId                    CfprManagedObjectId,
    cfprEquipmentBladeAggregationCapRefDn                            CfprManagedObjectDn,
    cfprEquipmentBladeAggregationCapRefRn                            SnmpAdminString,
    cfprEquipmentBladeAggregationCapRefIsSupported                   TruthValue
}

cfprEquipmentBladeAggregationCapRefInstanceId OBJECT-TYPE
    SYNTAX       CfprManagedObjectId
    MAX-ACCESS   not-accessible
    STATUS       current
    DESCRIPTION
        "Instance identifier of the managed object."
    ::= { cfprEquipmentBladeAggregationCapRefEntry 1 }

cfprEquipmentBladeAggregationCapRefDn OBJECT-TYPE
    SYNTAX       CfprManagedObjectDn
    MAX-ACCESS   read-only
    STATUS       current
    DESCRIPTION
        "Cisco Firepower equipment:BladeAggregationCapRef:dn
        managed object property"
    ::= { cfprEquipmentBladeAggregationCapRefEntry 2 }

cfprEquipmentBladeAggregationCapRefRn OBJECT-TYPE
    SYNTAX       SnmpAdminString
    MAX-ACCESS   read-only
    STATUS       current
    DESCRIPTION
        "Cisco Firepower equipment:BladeAggregationCapRef:rn
        managed object property"
    ::= { cfprEquipmentBladeAggregationCapRefEntry 3 }

cfprEquipmentBladeAggregationCapRefIsSupported OBJECT-TYPE
    SYNTAX       TruthValue
    MAX-ACCESS   read-only
    STATUS       current
    DESCRIPTION
        "Cisco Firepower equipment:BladeAggregationCapRef:isSupported
        managed object property"
    ::= { cfprEquipmentBladeAggregationCapRefEntry 4 }

cfprEquipmentBladeBiosCapProviderTable OBJECT-TYPE
    SYNTAX           SEQUENCE OF CfprEquipmentBladeBiosCapProviderEntry
    MAX-ACCESS       not-accessible
    STATUS           current
    DESCRIPTION
        "Cisco Firepower equipment:BladeBiosCapProvider
        managed object table"
    ::= { cfprEquipmentObjects 13 }

cfprEquipmentBladeBiosCapProviderEntry OBJECT-TYPE
    SYNTAX           CfprEquipmentBladeBiosCapProviderEntry
    MAX-ACCESS       not-accessible
    STATUS           current
    DESCRIPTION
        "Entry for the cfprEquipmentBladeBiosCapProviderTable table."
    INDEX { cfprEquipmentBladeBiosCapProviderInstanceId }
    ::= { cfprEquipmentBladeBiosCapProviderTable 1 }

CfprEquipmentBladeBiosCapProviderEntry ::= SEQUENCE {
    cfprEquipmentBladeBiosCapProviderInstanceId                      CfprManagedObjectId,
    cfprEquipmentBladeBiosCapProviderDn                              CfprManagedObjectDn,
    cfprEquipmentBladeBiosCapProviderRn                              SnmpAdminString,
    cfprEquipmentBladeBiosCapProviderDeleted                         TruthValue,
    cfprEquipmentBladeBiosCapProviderDeprecated                      TruthValue,
    cfprEquipmentBladeBiosCapProviderElementLoadFailures             Gauge32,
    cfprEquipmentBladeBiosCapProviderElementsLoaded                  Gauge32,
    cfprEquipmentBladeBiosCapProviderGencount                        Gauge32,
    cfprEquipmentBladeBiosCapProviderLoadErrors                      Gauge32,
    cfprEquipmentBladeBiosCapProviderLoadWarnings                    Gauge32,
    cfprEquipmentBladeBiosCapProviderMgmtPlaneVer                    SnmpAdminString,
    cfprEquipmentBladeBiosCapProviderModel                           SnmpAdminString,
    cfprEquipmentBladeBiosCapProviderProductName                     SnmpAdminString,
    cfprEquipmentBladeBiosCapProviderPromCardType                    Gauge32,
    cfprEquipmentBladeBiosCapProviderRevision                        SnmpAdminString,
    cfprEquipmentBladeBiosCapProviderVendor                          SnmpAdminString
}

cfprEquipmentBladeBiosCapProviderInstanceId OBJECT-TYPE
    SYNTAX       CfprManagedObjectId
    MAX-ACCESS   not-accessible
    STATUS       current
    DESCRIPTION
        "Instance identifier of the managed object."
    ::= { cfprEquipmentBladeBiosCapProviderEntry 1 }

cfprEquipmentBladeBiosCapProviderDn OBJECT-TYPE
    SYNTAX       CfprManagedObjectDn
    MAX-ACCESS   read-only
    STATUS       current
    DESCRIPTION
        "Cisco Firepower equipment:BladeBiosCapProvider:dn
        managed object property"
    ::= { cfprEquipmentBladeBiosCapProviderEntry 2 }

cfprEquipmentBladeBiosCapProviderRn OBJECT-TYPE
    SYNTAX       SnmpAdminString
    MAX-ACCESS   read-only
    STATUS       current
    DESCRIPTION
        "Cisco Firepower equipment:BladeBiosCapProvider:rn
        managed object property"
    ::= { cfprEquipmentBladeBiosCapProviderEntry 3 }

cfprEquipmentBladeBiosCapProviderDeleted OBJECT-TYPE
    SYNTAX       TruthValue
    MAX-ACCESS   read-only
    STATUS       current
    DESCRIPTION
        "Cisco Firepower equipment:BladeBiosCapProvider:deleted
        managed object property"
    ::= { cfprEquipmentBladeBiosCapProviderEntry 4 }

cfprEquipmentBladeBiosCapProviderDeprecated OBJECT-TYPE
    SYNTAX       TruthValue
    MAX-ACCESS   read-only
    STATUS       current
    DESCRIPTION
        "Cisco Firepower equipment:BladeBiosCapProvider:deprecated
        managed object property"
    ::= { cfprEquipmentBladeBiosCapProviderEntry 5 }

cfprEquipmentBladeBiosCapProviderElementLoadFailures OBJECT-TYPE
    SYNTAX       Gauge32
    MAX-ACCESS   read-only
    STATUS       current
    DESCRIPTION
        "Cisco Firepower equipment:BladeBiosCapProvider:elementLoadFailure
        s managed object property"
    ::= { cfprEquipmentBladeBiosCapProviderEntry 6 }

cfprEquipmentBladeBiosCapProviderElementsLoaded OBJECT-TYPE
    SYNTAX       Gauge32
    MAX-ACCESS   read-only
    STATUS       current
    DESCRIPTION
        "Cisco Firepower equipment:BladeBiosCapProvider:elementsLoaded
        managed object property"
    ::= { cfprEquipmentBladeBiosCapProviderEntry 7 }

cfprEquipmentBladeBiosCapProviderGencount OBJECT-TYPE
    SYNTAX       Gauge32
    MAX-ACCESS   read-only
    STATUS       current
    DESCRIPTION
        "Cisco Firepower equipment:BladeBiosCapProvider:gencount
        managed object property"
    ::= { cfprEquipmentBladeBiosCapProviderEntry 8 }

cfprEquipmentBladeBiosCapProviderLoadErrors OBJECT-TYPE
    SYNTAX       Gauge32
    MAX-ACCESS   read-only
    STATUS       current
    DESCRIPTION
        "Cisco Firepower equipment:BladeBiosCapProvider:loadErrors
        managed object property"
    ::= { cfprEquipmentBladeBiosCapProviderEntry 9 }

cfprEquipmentBladeBiosCapProviderLoadWarnings OBJECT-TYPE
    SYNTAX       Gauge32
    MAX-ACCESS   read-only
    STATUS       current
    DESCRIPTION
        "Cisco Firepower equipment:BladeBiosCapProvider:loadWarnings
        managed object property"
    ::= { cfprEquipmentBladeBiosCapProviderEntry 10 }

cfprEquipmentBladeBiosCapProviderMgmtPlaneVer OBJECT-TYPE
    SYNTAX       SnmpAdminString
    MAX-ACCESS   read-only
    STATUS       current
    DESCRIPTION
        "Cisco Firepower equipment:BladeBiosCapProvider:mgmtPlaneVer
        managed object property"
    ::= { cfprEquipmentBladeBiosCapProviderEntry 11 }

cfprEquipmentBladeBiosCapProviderModel OBJECT-TYPE
    SYNTAX       SnmpAdminString
    MAX-ACCESS   read-only
    STATUS       current
    DESCRIPTION
        "Cisco Firepower equipment:BladeBiosCapProvider:model
        managed object property"
    ::= { cfprEquipmentBladeBiosCapProviderEntry 12 }

cfprEquipmentBladeBiosCapProviderProductName OBJECT-TYPE
    SYNTAX       SnmpAdminString
    MAX-ACCESS   read-only
    STATUS       current
    DESCRIPTION
        "Cisco Firepower equipment:BladeBiosCapProvider:productName
        managed object property"
    ::= { cfprEquipmentBladeBiosCapProviderEntry 13 }

cfprEquipmentBladeBiosCapProviderPromCardType OBJECT-TYPE
    SYNTAX       Gauge32
    MAX-ACCESS   read-only
    STATUS       current
    DESCRIPTION
        "Cisco Firepower equipment:BladeBiosCapProvider:promCardType
        managed object property"
    ::= { cfprEquipmentBladeBiosCapProviderEntry 14 }

cfprEquipmentBladeBiosCapProviderRevision OBJECT-TYPE
    SYNTAX       SnmpAdminString
    MAX-ACCESS   read-only
    STATUS       current
    DESCRIPTION
        "Cisco Firepower equipment:BladeBiosCapProvider:revision
        managed object property"
    ::= { cfprEquipmentBladeBiosCapProviderEntry 15 }

cfprEquipmentBladeBiosCapProviderVendor OBJECT-TYPE
    SYNTAX       SnmpAdminString
    MAX-ACCESS   read-only
    STATUS       current
    DESCRIPTION
        "Cisco Firepower equipment:BladeBiosCapProvider:vendor
        managed object property"
    ::= { cfprEquipmentBladeBiosCapProviderEntry 16 }

cfprEquipmentBladeCapProviderTable OBJECT-TYPE
    SYNTAX           SEQUENCE OF CfprEquipmentBladeCapProviderEntry
    MAX-ACCESS       not-accessible
    STATUS           current
    DESCRIPTION
        "Cisco Firepower equipment:BladeCapProvider managed object table"
    ::= { cfprEquipmentObjects 14 }

cfprEquipmentBladeCapProviderEntry OBJECT-TYPE
    SYNTAX           CfprEquipmentBladeCapProviderEntry
    MAX-ACCESS       not-accessible
    STATUS           current
    DESCRIPTION
        "Entry for the cfprEquipmentBladeCapProviderTable table."
    INDEX { cfprEquipmentBladeCapProviderInstanceId }
    ::= { cfprEquipmentBladeCapProviderTable 1 }

CfprEquipmentBladeCapProviderEntry ::= SEQUENCE {
    cfprEquipmentBladeCapProviderInstanceId                          CfprManagedObjectId,
    cfprEquipmentBladeCapProviderDn                                  CfprManagedObjectDn,
    cfprEquipmentBladeCapProviderRn                                  SnmpAdminString,
    cfprEquipmentBladeCapProviderDeleted                             TruthValue,
    cfprEquipmentBladeCapProviderDeprecated                          TruthValue,
    cfprEquipmentBladeCapProviderElementLoadFailures                 Gauge32,
    cfprEquipmentBladeCapProviderElementsLoaded                      Gauge32,
    cfprEquipmentBladeCapProviderGencount                            Gauge32,
    cfprEquipmentBladeCapProviderLoadErrors                          Gauge32,
    cfprEquipmentBladeCapProviderLoadWarnings                        Gauge32,
    cfprEquipmentBladeCapProviderMgmtPlaneVer                        SnmpAdminString,
    cfprEquipmentBladeCapProviderModel                               SnmpAdminString,
    cfprEquipmentBladeCapProviderPromCardType                        Gauge32,
    cfprEquipmentBladeCapProviderRevision                            SnmpAdminString,
    cfprEquipmentBladeCapProviderVendor                              SnmpAdminString,
    cfprEquipmentBladeCapProviderGeneration                          Gauge32
}

cfprEquipmentBladeCapProviderInstanceId OBJECT-TYPE
    SYNTAX       CfprManagedObjectId
    MAX-ACCESS   not-accessible
    STATUS       current
    DESCRIPTION
        "Instance identifier of the managed object."
    ::= { cfprEquipmentBladeCapProviderEntry 1 }

cfprEquipmentBladeCapProviderDn OBJECT-TYPE
    SYNTAX       CfprManagedObjectDn
    MAX-ACCESS   read-only
    STATUS       current
    DESCRIPTION
        "Cisco Firepower equipment:BladeCapProvider:dn
        managed object property"
    ::= { cfprEquipmentBladeCapProviderEntry 2 }

cfprEquipmentBladeCapProviderRn OBJECT-TYPE
    SYNTAX       SnmpAdminString
    MAX-ACCESS   read-only
    STATUS       current
    DESCRIPTION
        "Cisco Firepower equipment:BladeCapProvider:rn
        managed object property"
    ::= { cfprEquipmentBladeCapProviderEntry 3 }

cfprEquipmentBladeCapProviderDeleted OBJECT-TYPE
    SYNTAX       TruthValue
    MAX-ACCESS   read-only
    STATUS       current
    DESCRIPTION
        "Cisco Firepower equipment:BladeCapProvider:deleted
        managed object property"
    ::= { cfprEquipmentBladeCapProviderEntry 4 }

cfprEquipmentBladeCapProviderDeprecated OBJECT-TYPE
    SYNTAX       TruthValue
    MAX-ACCESS   read-only
    STATUS       current
    DESCRIPTION
        "Cisco Firepower equipment:BladeCapProvider:deprecated
        managed object property"
    ::= { cfprEquipmentBladeCapProviderEntry 5 }

cfprEquipmentBladeCapProviderElementLoadFailures OBJECT-TYPE
    SYNTAX       Gauge32
    MAX-ACCESS   read-only
    STATUS       current
    DESCRIPTION
        "Cisco Firepower equipment:BladeCapProvider:elementLoadFailures
        managed object property"
    ::= { cfprEquipmentBladeCapProviderEntry 6 }

cfprEquipmentBladeCapProviderElementsLoaded OBJECT-TYPE
    SYNTAX       Gauge32
    MAX-ACCESS   read-only
    STATUS       current
    DESCRIPTION
        "Cisco Firepower equipment:BladeCapProvider:elementsLoaded
        managed object property"
    ::= { cfprEquipmentBladeCapProviderEntry 7 }

cfprEquipmentBladeCapProviderGencount OBJECT-TYPE
    SYNTAX       Gauge32
    MAX-ACCESS   read-only
    STATUS       current
    DESCRIPTION
        "Cisco Firepower equipment:BladeCapProvider:gencount
        managed object property"
    ::= { cfprEquipmentBladeCapProviderEntry 8 }

cfprEquipmentBladeCapProviderLoadErrors OBJECT-TYPE
    SYNTAX       Gauge32
    MAX-ACCESS   read-only
    STATUS       current
    DESCRIPTION
        "Cisco Firepower equipment:BladeCapProvider:loadErrors
        managed object property"
    ::= { cfprEquipmentBladeCapProviderEntry 9 }

cfprEquipmentBladeCapProviderLoadWarnings OBJECT-TYPE
    SYNTAX       Gauge32
    MAX-ACCESS   read-only
    STATUS       current
    DESCRIPTION
        "Cisco Firepower equipment:BladeCapProvider:loadWarnings
        managed object property"
    ::= { cfprEquipmentBladeCapProviderEntry 10 }

cfprEquipmentBladeCapProviderMgmtPlaneVer OBJECT-TYPE
    SYNTAX       SnmpAdminString
    MAX-ACCESS   read-only
    STATUS       current
    DESCRIPTION
        "Cisco Firepower equipment:BladeCapProvider:mgmtPlaneVer
        managed object property"
    ::= { cfprEquipmentBladeCapProviderEntry 11 }

cfprEquipmentBladeCapProviderModel OBJECT-TYPE
    SYNTAX       SnmpAdminString
    MAX-ACCESS   read-only
    STATUS       current
    DESCRIPTION
        "Cisco Firepower equipment:BladeCapProvider:model
        managed object property"
    ::= { cfprEquipmentBladeCapProviderEntry 12 }

cfprEquipmentBladeCapProviderPromCardType OBJECT-TYPE
    SYNTAX       Gauge32
    MAX-ACCESS   read-only
    STATUS       current
    DESCRIPTION
        "Cisco Firepower equipment:BladeCapProvider:promCardType
        managed object property"
    ::= { cfprEquipmentBladeCapProviderEntry 13 }

cfprEquipmentBladeCapProviderRevision OBJECT-TYPE
    SYNTAX       SnmpAdminString
    MAX-ACCESS   read-only
    STATUS       current
    DESCRIPTION
        "Cisco Firepower equipment:BladeCapProvider:revision
        managed object property"
    ::= { cfprEquipmentBladeCapProviderEntry 14 }

cfprEquipmentBladeCapProviderVendor OBJECT-TYPE
    SYNTAX       SnmpAdminString
    MAX-ACCESS   read-only
    STATUS       current
    DESCRIPTION
        "Cisco Firepower equipment:BladeCapProvider:vendor
        managed object property"
    ::= { cfprEquipmentBladeCapProviderEntry 15 }

cfprEquipmentBladeCapProviderGeneration OBJECT-TYPE
    SYNTAX       Gauge32
    MAX-ACCESS   read-only
    STATUS       current
    DESCRIPTION
        "Cisco Firepower equipment:BladeCapProvider:generation
        managed object property"
    ::= { cfprEquipmentBladeCapProviderEntry 16 }

cfprEquipmentBladeCapProviderTypeDefTable OBJECT-TYPE
    SYNTAX           SEQUENCE OF CfprEquipmentBladeCapProviderTypeDefEntry
    MAX-ACCESS       not-accessible
    STATUS           current
    DESCRIPTION
        "Cisco Firepower equipment:BladeCapProviderTypeDef
        managed object table"
    ::= { cfprEquipmentObjects 145 }

cfprEquipmentBladeCapProviderTypeDefEntry OBJECT-TYPE
    SYNTAX           CfprEquipmentBladeCapProviderTypeDefEntry
    MAX-ACCESS       not-accessible
    STATUS           current
    DESCRIPTION
        "Entry for the cfprEquipmentBladeCapProviderTypeDefTable table."
    INDEX { cfprEquipmentBladeCapProviderTypeDefInstanceId }
    ::= { cfprEquipmentBladeCapProviderTypeDefTable 1 }

CfprEquipmentBladeCapProviderTypeDefEntry ::= SEQUENCE {
    cfprEquipmentBladeCapProviderTypeDefInstanceId                   CfprManagedObjectId,
    cfprEquipmentBladeCapProviderTypeDefDn                           CfprManagedObjectDn,
    cfprEquipmentBladeCapProviderTypeDefRn                           SnmpAdminString,
    cfprEquipmentBladeCapProviderTypeDefNumAdapterSlots              Gauge32,
    cfprEquipmentBladeCapProviderTypeDefNumSlots                     Gauge32
}

cfprEquipmentBladeCapProviderTypeDefInstanceId OBJECT-TYPE
    SYNTAX       CfprManagedObjectId
    MAX-ACCESS   not-accessible
    STATUS       current
    DESCRIPTION
        "Instance identifier of the managed object."
    ::= { cfprEquipmentBladeCapProviderTypeDefEntry 1 }

cfprEquipmentBladeCapProviderTypeDefDn OBJECT-TYPE
    SYNTAX       CfprManagedObjectDn
    MAX-ACCESS   read-only
    STATUS       current
    DESCRIPTION
        "Cisco Firepower equipment:BladeCapProviderTypeDef:dn
        managed object property"
    ::= { cfprEquipmentBladeCapProviderTypeDefEntry 2 }

cfprEquipmentBladeCapProviderTypeDefRn OBJECT-TYPE
    SYNTAX       SnmpAdminString
    MAX-ACCESS   read-only
    STATUS       current
    DESCRIPTION
        "Cisco Firepower equipment:BladeCapProviderTypeDef:rn
        managed object property"
    ::= { cfprEquipmentBladeCapProviderTypeDefEntry 3 }

cfprEquipmentBladeCapProviderTypeDefNumAdapterSlots OBJECT-TYPE
    SYNTAX       Gauge32
    MAX-ACCESS   read-only
    STATUS       current
    DESCRIPTION
        "Cisco Firepower equipment:BladeCapProviderTypeDef:numAdapterSlots
         managed object property"
    ::= { cfprEquipmentBladeCapProviderTypeDefEntry 4 }

cfprEquipmentBladeCapProviderTypeDefNumSlots OBJECT-TYPE
    SYNTAX       Gauge32
    MAX-ACCESS   read-only
    STATUS       current
    DESCRIPTION
        "Cisco Firepower equipment:BladeCapProviderTypeDef:numSlots
        managed object property"
    ::= { cfprEquipmentBladeCapProviderTypeDefEntry 5 }

cfprEquipmentBladeConnDefTable OBJECT-TYPE
    SYNTAX           SEQUENCE OF CfprEquipmentBladeConnDefEntry
    MAX-ACCESS       not-accessible
    STATUS           current
    DESCRIPTION
        "Cisco Firepower equipment:BladeConnDef managed object table"
    ::= { cfprEquipmentObjects 15 }

cfprEquipmentBladeConnDefEntry OBJECT-TYPE
    SYNTAX           CfprEquipmentBladeConnDefEntry
    MAX-ACCESS       not-accessible
    STATUS           current
    DESCRIPTION
        "Entry for the cfprEquipmentBladeConnDefTable table."
    INDEX { cfprEquipmentBladeConnDefInstanceId }
    ::= { cfprEquipmentBladeConnDefTable 1 }

CfprEquipmentBladeConnDefEntry ::= SEQUENCE {
    cfprEquipmentBladeConnDefInstanceId                              CfprManagedObjectId,
    cfprEquipmentBladeConnDefDn                                      CfprManagedObjectDn,
    cfprEquipmentBladeConnDefRn                                      SnmpAdminString,
    cfprEquipmentBladeConnDefAdaptorFamily                           SnmpAdminString,
    cfprEquipmentBladeConnDefAdaptorSlotNumber                       Gauge32,
    cfprEquipmentBladeConnDefAdaptorSlotSpan                         Gauge32,
    cfprEquipmentBladeConnDefAdaptorType                             SnmpAdminString,
    cfprEquipmentBladeConnDefDescr                                   SnmpAdminString,
    cfprEquipmentBladeConnDefIntId                                   SnmpAdminString,
    cfprEquipmentBladeConnDefName                                    SnmpAdminString,
    cfprEquipmentBladeConnDefParentAdaptorSlotNum                    Gauge32,
    cfprEquipmentBladeConnDefPolicyLevel                             Gauge32,
    cfprEquipmentBladeConnDefPolicyOwner                             CfprPolicyPolicyOwner,
    cfprEquipmentBladeConnDefSwitchPortMuxOffset                     Gauge32
}

cfprEquipmentBladeConnDefInstanceId OBJECT-TYPE
    SYNTAX       CfprManagedObjectId
    MAX-ACCESS   not-accessible
    STATUS       current
    DESCRIPTION
        "Instance identifier of the managed object."
    ::= { cfprEquipmentBladeConnDefEntry 1 }

cfprEquipmentBladeConnDefDn OBJECT-TYPE
    SYNTAX       CfprManagedObjectDn
    MAX-ACCESS   read-only
    STATUS       current
    DESCRIPTION
        "Cisco Firepower equipment:BladeConnDef:dn managed
        object property"
    ::= { cfprEquipmentBladeConnDefEntry 2 }

cfprEquipmentBladeConnDefRn OBJECT-TYPE
    SYNTAX       SnmpAdminString
    MAX-ACCESS   read-only
    STATUS       current
    DESCRIPTION
        "Cisco Firepower equipment:BladeConnDef:rn managed
        object property"
    ::= { cfprEquipmentBladeConnDefEntry 3 }

cfprEquipmentBladeConnDefAdaptorFamily OBJECT-TYPE
    SYNTAX       SnmpAdminString
    MAX-ACCESS   read-only
    STATUS       current
    DESCRIPTION
        "Cisco Firepower equipment:BladeConnDef:adaptorFamily
        managed object property"
    ::= { cfprEquipmentBladeConnDefEntry 4 }

cfprEquipmentBladeConnDefAdaptorSlotNumber OBJECT-TYPE
    SYNTAX       Gauge32
    MAX-ACCESS   read-only
    STATUS       current
    DESCRIPTION
        "Cisco Firepower equipment:BladeConnDef:adaptorSlotNumber
        managed object property"
    ::= { cfprEquipmentBladeConnDefEntry 5 }

cfprEquipmentBladeConnDefAdaptorSlotSpan OBJECT-TYPE
    SYNTAX       Gauge32
    MAX-ACCESS   read-only
    STATUS       current
    DESCRIPTION
        "Cisco Firepower equipment:BladeConnDef:adaptorSlotSpan
        managed object property"
    ::= { cfprEquipmentBladeConnDefEntry 6 }

cfprEquipmentBladeConnDefAdaptorType OBJECT-TYPE
    SYNTAX       SnmpAdminString
    MAX-ACCESS   read-only
    STATUS       current
    DESCRIPTION
        "Cisco Firepower equipment:BladeConnDef:adaptorType
        managed object property"
    ::= { cfprEquipmentBladeConnDefEntry 7 }

cfprEquipmentBladeConnDefDescr OBJECT-TYPE
    SYNTAX       SnmpAdminString
    MAX-ACCESS   read-only
    STATUS       current
    DESCRIPTION
        "Cisco Firepower equipment:BladeConnDef:descr managed
        object property"
    ::= { cfprEquipmentBladeConnDefEntry 8 }

cfprEquipmentBladeConnDefIntId OBJECT-TYPE
    SYNTAX       SnmpAdminString
    MAX-ACCESS   read-only
    STATUS       current
    DESCRIPTION
        "Cisco Firepower equipment:BladeConnDef:intId managed
        object property"
    ::= { cfprEquipmentBladeConnDefEntry 9 }

cfprEquipmentBladeConnDefName OBJECT-TYPE
    SYNTAX       SnmpAdminString
    MAX-ACCESS   read-only
    STATUS       current
    DESCRIPTION
        "Cisco Firepower equipment:BladeConnDef:name managed
        object property"
    ::= { cfprEquipmentBladeConnDefEntry 10 }

cfprEquipmentBladeConnDefParentAdaptorSlotNum OBJECT-TYPE
    SYNTAX       Gauge32
    MAX-ACCESS   read-only
    STATUS       current
    DESCRIPTION
        "Cisco Firepower equipment:BladeConnDef:parentAdaptorSlotNum
        managed object property"
    ::= { cfprEquipmentBladeConnDefEntry 11 }

cfprEquipmentBladeConnDefPolicyLevel OBJECT-TYPE
    SYNTAX       Gauge32
    MAX-ACCESS   read-only
    STATUS       current
    DESCRIPTION
        "Cisco Firepower equipment:BladeConnDef:policyLevel
        managed object property"
    ::= { cfprEquipmentBladeConnDefEntry 12 }

cfprEquipmentBladeConnDefPolicyOwner OBJECT-TYPE
    SYNTAX       CfprPolicyPolicyOwner
    MAX-ACCESS   read-only
    STATUS       current
    DESCRIPTION
        "Cisco Firepower equipment:BladeConnDef:policyOwner
        managed object property"
    ::= { cfprEquipmentBladeConnDefEntry 13 }

cfprEquipmentBladeConnDefSwitchPortMuxOffset OBJECT-TYPE
    SYNTAX       Gauge32
    MAX-ACCESS   read-only
    STATUS       current
    DESCRIPTION
        "Cisco Firepower equipment:BladeConnDef:switchPortMuxOffset
        managed object property"
    ::= { cfprEquipmentBladeConnDefEntry 14 }

cfprEquipmentBladeEnvTable OBJECT-TYPE
    SYNTAX           SEQUENCE OF CfprEquipmentBladeEnvEntry
    MAX-ACCESS       not-accessible
    STATUS           current
    DESCRIPTION
        "Cisco Firepower equipment:BladeEnv managed object table"
    ::= { cfprEquipmentObjects 146 }

cfprEquipmentBladeEnvEntry OBJECT-TYPE
    SYNTAX           CfprEquipmentBladeEnvEntry
    MAX-ACCESS       not-accessible
    STATUS           current
    DESCRIPTION
        "Entry for the cfprEquipmentBladeEnvTable table."
    INDEX { cfprEquipmentBladeEnvInstanceId }
    ::= { cfprEquipmentBladeEnvTable 1 }

CfprEquipmentBladeEnvEntry ::= SEQUENCE {
    cfprEquipmentBladeEnvInstanceId                                  CfprManagedObjectId,
    cfprEquipmentBladeEnvDn                                          CfprManagedObjectDn,
    cfprEquipmentBladeEnvRn                                          SnmpAdminString,
    cfprEquipmentBladeEnvCpu1Temp                                    INTEGER,
    cfprEquipmentBladeEnvCpu2Temp                                    INTEGER,
    cfprEquipmentBladeEnvCpuTemp                                     INTEGER,
    cfprEquipmentBladeEnvId                                          Gauge32,
    cfprEquipmentBladeEnvOperStatus                                  SnmpAdminString,
    cfprEquipmentBladeEnvPowerConsumption                            INTEGER
}

cfprEquipmentBladeEnvInstanceId OBJECT-TYPE
    SYNTAX       CfprManagedObjectId
    MAX-ACCESS   not-accessible
    STATUS       current
    DESCRIPTION
        "Instance identifier of the managed object."
    ::= { cfprEquipmentBladeEnvEntry 1 }

cfprEquipmentBladeEnvDn OBJECT-TYPE
    SYNTAX       CfprManagedObjectDn
    MAX-ACCESS   read-only
    STATUS       current
    DESCRIPTION
        "Cisco Firepower equipment:BladeEnv:dn managed object property"
    ::= { cfprEquipmentBladeEnvEntry 2 }

cfprEquipmentBladeEnvRn OBJECT-TYPE
    SYNTAX       SnmpAdminString
    MAX-ACCESS   read-only
    STATUS       current
    DESCRIPTION
        "Cisco Firepower equipment:BladeEnv:rn managed object property"
    ::= { cfprEquipmentBladeEnvEntry 3 }

cfprEquipmentBladeEnvCpu1Temp OBJECT-TYPE
    SYNTAX       INTEGER
    MAX-ACCESS   read-only
    STATUS       current
    DESCRIPTION
        "Cisco Firepower equipment:BladeEnv:cpu1Temp managed
        object property"
    ::= { cfprEquipmentBladeEnvEntry 4 }

cfprEquipmentBladeEnvCpu2Temp OBJECT-TYPE
    SYNTAX       INTEGER
    MAX-ACCESS   read-only
    STATUS       current
    DESCRIPTION
        "Cisco Firepower equipment:BladeEnv:cpu2Temp managed
        object property"
    ::= { cfprEquipmentBladeEnvEntry 5 }

cfprEquipmentBladeEnvCpuTemp OBJECT-TYPE
    SYNTAX       INTEGER
    MAX-ACCESS   read-only
    STATUS       current
    DESCRIPTION
        "Cisco Firepower equipment:BladeEnv:cpuTemp managed
        object property"
    ::= { cfprEquipmentBladeEnvEntry 6 }

cfprEquipmentBladeEnvId OBJECT-TYPE
    SYNTAX       Gauge32
    MAX-ACCESS   read-only
    STATUS       current
    DESCRIPTION
        "Cisco Firepower equipment:BladeEnv:id managed object property"
    ::= { cfprEquipmentBladeEnvEntry 7 }

cfprEquipmentBladeEnvOperStatus OBJECT-TYPE
    SYNTAX       SnmpAdminString
    MAX-ACCESS   read-only
    STATUS       current
    DESCRIPTION
        "Cisco Firepower equipment:BladeEnv:operStatus
        managed object property"
    ::= { cfprEquipmentBladeEnvEntry 8 }

cfprEquipmentBladeEnvPowerConsumption OBJECT-TYPE
    SYNTAX       INTEGER
    MAX-ACCESS   read-only
    STATUS       current
    DESCRIPTION
        "Cisco Firepower equipment:BladeEnv:powerConsumption
        managed object property"
    ::= { cfprEquipmentBladeEnvEntry 9 }

cfprEquipmentBladeIOMConnDefTable OBJECT-TYPE
    SYNTAX           SEQUENCE OF CfprEquipmentBladeIOMConnDefEntry
    MAX-ACCESS       not-accessible
    STATUS           current
    DESCRIPTION
        "Cisco Firepower equipment:BladeIOMConnDef managed object table"
    ::= { cfprEquipmentObjects 16 }

cfprEquipmentBladeIOMConnDefEntry OBJECT-TYPE
    SYNTAX           CfprEquipmentBladeIOMConnDefEntry
    MAX-ACCESS       not-accessible
    STATUS           current
    DESCRIPTION
        "Entry for the cfprEquipmentBladeIOMConnDefTable table."
    INDEX { cfprEquipmentBladeIOMConnDefInstanceId }
    ::= { cfprEquipmentBladeIOMConnDefTable 1 }

CfprEquipmentBladeIOMConnDefEntry ::= SEQUENCE {
    cfprEquipmentBladeIOMConnDefInstanceId                           CfprManagedObjectId,
    cfprEquipmentBladeIOMConnDefDn                                   CfprManagedObjectDn,
    cfprEquipmentBladeIOMConnDefRn                                   SnmpAdminString,
    cfprEquipmentBladeIOMConnDefDescr                                SnmpAdminString,
    cfprEquipmentBladeIOMConnDefIntId                                SnmpAdminString,
    cfprEquipmentBladeIOMConnDefIocardType                           SnmpAdminString,
    cfprEquipmentBladeIOMConnDefName                                 SnmpAdminString,
    cfprEquipmentBladeIOMConnDefPolicyLevel                          Gauge32,
    cfprEquipmentBladeIOMConnDefPolicyOwner                          CfprPolicyPolicyOwner,
    cfprEquipmentBladeIOMConnDefPortBandwidth                        CfprPortEthSpeed
}

cfprEquipmentBladeIOMConnDefInstanceId OBJECT-TYPE
    SYNTAX       CfprManagedObjectId
    MAX-ACCESS   not-accessible
    STATUS       current
    DESCRIPTION
        "Instance identifier of the managed object."
    ::= { cfprEquipmentBladeIOMConnDefEntry 1 }

cfprEquipmentBladeIOMConnDefDn OBJECT-TYPE
    SYNTAX       CfprManagedObjectDn
    MAX-ACCESS   read-only
    STATUS       current
    DESCRIPTION
        "Cisco Firepower equipment:BladeIOMConnDef:dn managed
        object property"
    ::= { cfprEquipmentBladeIOMConnDefEntry 2 }

cfprEquipmentBladeIOMConnDefRn OBJECT-TYPE
    SYNTAX       SnmpAdminString
    MAX-ACCESS   read-only
    STATUS       current
    DESCRIPTION
        "Cisco Firepower equipment:BladeIOMConnDef:rn managed
        object property"
    ::= { cfprEquipmentBladeIOMConnDefEntry 3 }

cfprEquipmentBladeIOMConnDefDescr OBJECT-TYPE
    SYNTAX       SnmpAdminString
    MAX-ACCESS   read-only
    STATUS       current
    DESCRIPTION
        "Cisco Firepower equipment:BladeIOMConnDef:descr
        managed object property"
    ::= { cfprEquipmentBladeIOMConnDefEntry 4 }

cfprEquipmentBladeIOMConnDefIntId OBJECT-TYPE
    SYNTAX       SnmpAdminString
    MAX-ACCESS   read-only
    STATUS       current
    DESCRIPTION
        "Cisco Firepower equipment:BladeIOMConnDef:intId
        managed object property"
    ::= { cfprEquipmentBladeIOMConnDefEntry 5 }

cfprEquipmentBladeIOMConnDefIocardType OBJECT-TYPE
    SYNTAX       SnmpAdminString
    MAX-ACCESS   read-only
    STATUS       current
    DESCRIPTION
        "Cisco Firepower equipment:BladeIOMConnDef:iocardType
        managed object property"
    ::= { cfprEquipmentBladeIOMConnDefEntry 6 }

cfprEquipmentBladeIOMConnDefName OBJECT-TYPE
    SYNTAX       SnmpAdminString
    MAX-ACCESS   read-only
    STATUS       current
    DESCRIPTION
        "Cisco Firepower equipment:BladeIOMConnDef:name
        managed object property"
    ::= { cfprEquipmentBladeIOMConnDefEntry 7 }

cfprEquipmentBladeIOMConnDefPolicyLevel OBJECT-TYPE
    SYNTAX       Gauge32
    MAX-ACCESS   read-only
    STATUS       current
    DESCRIPTION
        "Cisco Firepower equipment:BladeIOMConnDef:policyLevel
        managed object property"
    ::= { cfprEquipmentBladeIOMConnDefEntry 8 }

cfprEquipmentBladeIOMConnDefPolicyOwner OBJECT-TYPE
    SYNTAX       CfprPolicyPolicyOwner
    MAX-ACCESS   read-only
    STATUS       current
    DESCRIPTION
        "Cisco Firepower equipment:BladeIOMConnDef:policyOwner
        managed object property"
    ::= { cfprEquipmentBladeIOMConnDefEntry 9 }

cfprEquipmentBladeIOMConnDefPortBandwidth OBJECT-TYPE
    SYNTAX       CfprPortEthSpeed
    MAX-ACCESS   read-only
    STATUS       current
    DESCRIPTION
        "Cisco Firepower equipment:BladeIOMConnDef:portBandwidth
        managed object property"
    ::= { cfprEquipmentBladeIOMConnDefEntry 10 }

cfprEquipmentBladeSwitchConnDefTable OBJECT-TYPE
    SYNTAX           SEQUENCE OF CfprEquipmentBladeSwitchConnDefEntry
    MAX-ACCESS       not-accessible
    STATUS           current
    DESCRIPTION
        "Cisco Firepower equipment:BladeSwitchConnDef managed
        object table"
    ::= { cfprEquipmentObjects 17 }

cfprEquipmentBladeSwitchConnDefEntry OBJECT-TYPE
    SYNTAX           CfprEquipmentBladeSwitchConnDefEntry
    MAX-ACCESS       not-accessible
    STATUS           current
    DESCRIPTION
        "Entry for the cfprEquipmentBladeSwitchConnDefTable table."
    INDEX { cfprEquipmentBladeSwitchConnDefInstanceId }
    ::= { cfprEquipmentBladeSwitchConnDefTable 1 }

CfprEquipmentBladeSwitchConnDefEntry ::= SEQUENCE {
    cfprEquipmentBladeSwitchConnDefInstanceId                        CfprManagedObjectId,
    cfprEquipmentBladeSwitchConnDefDn                                CfprManagedObjectDn,
    cfprEquipmentBladeSwitchConnDefRn                                SnmpAdminString,
    cfprEquipmentBladeSwitchConnDefDescr                             SnmpAdminString,
    cfprEquipmentBladeSwitchConnDefIntId                             SnmpAdminString,
    cfprEquipmentBladeSwitchConnDefName                              SnmpAdminString,
    cfprEquipmentBladeSwitchConnDefPolicyLevel                       Gauge32,
    cfprEquipmentBladeSwitchConnDefPolicyOwner                       CfprPolicyPolicyOwner,
    cfprEquipmentBladeSwitchConnDefPortBandwidth                     CfprPortEthSpeed,
    cfprEquipmentBladeSwitchConnDefSwitchType                        SnmpAdminString
}

cfprEquipmentBladeSwitchConnDefInstanceId OBJECT-TYPE
    SYNTAX       CfprManagedObjectId
    MAX-ACCESS   not-accessible
    STATUS       current
    DESCRIPTION
        "Instance identifier of the managed object."
    ::= { cfprEquipmentBladeSwitchConnDefEntry 1 }

cfprEquipmentBladeSwitchConnDefDn OBJECT-TYPE
    SYNTAX       CfprManagedObjectDn
    MAX-ACCESS   read-only
    STATUS       current
    DESCRIPTION
        "Cisco Firepower equipment:BladeSwitchConnDef:dn
        managed object property"
    ::= { cfprEquipmentBladeSwitchConnDefEntry 2 }

cfprEquipmentBladeSwitchConnDefRn OBJECT-TYPE
    SYNTAX       SnmpAdminString
    MAX-ACCESS   read-only
    STATUS       current
    DESCRIPTION
        "Cisco Firepower equipment:BladeSwitchConnDef:rn
        managed object property"
    ::= { cfprEquipmentBladeSwitchConnDefEntry 3 }

cfprEquipmentBladeSwitchConnDefDescr OBJECT-TYPE
    SYNTAX       SnmpAdminString
    MAX-ACCESS   read-only
    STATUS       current
    DESCRIPTION
        "Cisco Firepower equipment:BladeSwitchConnDef:descr
        managed object property"
    ::= { cfprEquipmentBladeSwitchConnDefEntry 4 }

cfprEquipmentBladeSwitchConnDefIntId OBJECT-TYPE
    SYNTAX       SnmpAdminString
    MAX-ACCESS   read-only
    STATUS       current
    DESCRIPTION
        "Cisco Firepower equipment:BladeSwitchConnDef:intId
        managed object property"
    ::= { cfprEquipmentBladeSwitchConnDefEntry 5 }

cfprEquipmentBladeSwitchConnDefName OBJECT-TYPE
    SYNTAX       SnmpAdminString
    MAX-ACCESS   read-only
    STATUS       current
    DESCRIPTION
        "Cisco Firepower equipment:BladeSwitchConnDef:name
        managed object property"
    ::= { cfprEquipmentBladeSwitchConnDefEntry 6 }

cfprEquipmentBladeSwitchConnDefPolicyLevel OBJECT-TYPE
    SYNTAX       Gauge32
    MAX-ACCESS   read-only
    STATUS       current
    DESCRIPTION
        "Cisco Firepower equipment:BladeSwitchConnDef:policyLevel
        managed object property"
    ::= { cfprEquipmentBladeSwitchConnDefEntry 7 }

cfprEquipmentBladeSwitchConnDefPolicyOwner OBJECT-TYPE
    SYNTAX       CfprPolicyPolicyOwner
    MAX-ACCESS   read-only
    STATUS       current
    DESCRIPTION
        "Cisco Firepower equipment:BladeSwitchConnDef:policyOwner
        managed object property"
    ::= { cfprEquipmentBladeSwitchConnDefEntry 8 }

cfprEquipmentBladeSwitchConnDefPortBandwidth OBJECT-TYPE
    SYNTAX       CfprPortEthSpeed
    MAX-ACCESS   read-only
    STATUS       current
    DESCRIPTION
        "Cisco Firepower equipment:BladeSwitchConnDef:portBandwidth
        managed object property"
    ::= { cfprEquipmentBladeSwitchConnDefEntry 9 }

cfprEquipmentBladeSwitchConnDefSwitchType OBJECT-TYPE
    SYNTAX       SnmpAdminString
    MAX-ACCESS   read-only
    STATUS       current
    DESCRIPTION
        "Cisco Firepower equipment:BladeSwitchConnDef:switchType
        managed object property"
    ::= { cfprEquipmentBladeSwitchConnDefEntry 10 }

cfprEquipmentBoardControllerDefTable OBJECT-TYPE
    SYNTAX           SEQUENCE OF CfprEquipmentBoardControllerDefEntry
    MAX-ACCESS       not-accessible
    STATUS           current
    DESCRIPTION
        "Cisco Firepower equipment:BoardControllerDef managed
        object table"
    ::= { cfprEquipmentObjects 18 }

cfprEquipmentBoardControllerDefEntry OBJECT-TYPE
    SYNTAX           CfprEquipmentBoardControllerDefEntry
    MAX-ACCESS       not-accessible
    STATUS           current
    DESCRIPTION
        "Entry for the cfprEquipmentBoardControllerDefTable table."
    INDEX { cfprEquipmentBoardControllerDefInstanceId }
    ::= { cfprEquipmentBoardControllerDefTable 1 }

CfprEquipmentBoardControllerDefEntry ::= SEQUENCE {
    cfprEquipmentBoardControllerDefInstanceId                        CfprManagedObjectId,
    cfprEquipmentBoardControllerDefDn                                CfprManagedObjectDn,
    cfprEquipmentBoardControllerDefRn                                SnmpAdminString,
    cfprEquipmentBoardControllerDefDescr                             SnmpAdminString,
    cfprEquipmentBoardControllerDefIntId                             SnmpAdminString,
    cfprEquipmentBoardControllerDefName                              SnmpAdminString,
    cfprEquipmentBoardControllerDefPolicyLevel                       Gauge32,
    cfprEquipmentBoardControllerDefPolicyOwner                       CfprPolicyPolicyOwner
}

cfprEquipmentBoardControllerDefInstanceId OBJECT-TYPE
    SYNTAX       CfprManagedObjectId
    MAX-ACCESS   not-accessible
    STATUS       current
    DESCRIPTION
        "Instance identifier of the managed object."
    ::= { cfprEquipmentBoardControllerDefEntry 1 }

cfprEquipmentBoardControllerDefDn OBJECT-TYPE
    SYNTAX       CfprManagedObjectDn
    MAX-ACCESS   read-only
    STATUS       current
    DESCRIPTION
        "Cisco Firepower equipment:BoardControllerDef:dn
        managed object property"
    ::= { cfprEquipmentBoardControllerDefEntry 2 }

cfprEquipmentBoardControllerDefRn OBJECT-TYPE
    SYNTAX       SnmpAdminString
    MAX-ACCESS   read-only
    STATUS       current
    DESCRIPTION
        "Cisco Firepower equipment:BoardControllerDef:rn
        managed object property"
    ::= { cfprEquipmentBoardControllerDefEntry 3 }

cfprEquipmentBoardControllerDefDescr OBJECT-TYPE
    SYNTAX       SnmpAdminString
    MAX-ACCESS   read-only
    STATUS       current
    DESCRIPTION
        "Cisco Firepower equipment:BoardControllerDef:descr
        managed object property"
    ::= { cfprEquipmentBoardControllerDefEntry 4 }

cfprEquipmentBoardControllerDefIntId OBJECT-TYPE
    SYNTAX       SnmpAdminString
    MAX-ACCESS   read-only
    STATUS       current
    DESCRIPTION
        "Cisco Firepower equipment:BoardControllerDef:intId
        managed object property"
    ::= { cfprEquipmentBoardControllerDefEntry 5 }

cfprEquipmentBoardControllerDefName OBJECT-TYPE
    SYNTAX       SnmpAdminString
    MAX-ACCESS   read-only
    STATUS       current
    DESCRIPTION
        "Cisco Firepower equipment:BoardControllerDef:name
        managed object property"
    ::= { cfprEquipmentBoardControllerDefEntry 6 }

cfprEquipmentBoardControllerDefPolicyLevel OBJECT-TYPE
    SYNTAX       Gauge32
    MAX-ACCESS   read-only
    STATUS       current
    DESCRIPTION
        "Cisco Firepower equipment:BoardControllerDef:policyLevel
        managed object property"
    ::= { cfprEquipmentBoardControllerDefEntry 7 }

cfprEquipmentBoardControllerDefPolicyOwner OBJECT-TYPE
    SYNTAX       CfprPolicyPolicyOwner
    MAX-ACCESS   read-only
    STATUS       current
    DESCRIPTION
        "Cisco Firepower equipment:BoardControllerDef:policyOwner
        managed object property"
    ::= { cfprEquipmentBoardControllerDefEntry 8 }

cfprEquipmentBreakOutCapProviderTable OBJECT-TYPE
    SYNTAX           SEQUENCE OF CfprEquipmentBreakOutCapProviderEntry
    MAX-ACCESS       not-accessible
    STATUS           current
    DESCRIPTION
        "Cisco Firepower equipment:BreakOutCapProvider
        managed object table"
    ::= { cfprEquipmentObjects 19 }

cfprEquipmentBreakOutCapProviderEntry OBJECT-TYPE
    SYNTAX           CfprEquipmentBreakOutCapProviderEntry
    MAX-ACCESS       not-accessible
    STATUS           current
    DESCRIPTION
        "Entry for the cfprEquipmentBreakOutCapProviderTable table."
    INDEX { cfprEquipmentBreakOutCapProviderInstanceId }
    ::= { cfprEquipmentBreakOutCapProviderTable 1 }

CfprEquipmentBreakOutCapProviderEntry ::= SEQUENCE {
    cfprEquipmentBreakOutCapProviderInstanceId                       CfprManagedObjectId,
    cfprEquipmentBreakOutCapProviderDn                               CfprManagedObjectDn,
    cfprEquipmentBreakOutCapProviderRn                               SnmpAdminString,
    cfprEquipmentBreakOutCapProviderBreakoutSupported                TruthValue,
    cfprEquipmentBreakOutCapProviderDescr                            SnmpAdminString,
    cfprEquipmentBreakOutCapProviderIntId                            SnmpAdminString,
    cfprEquipmentBreakOutCapProviderName                             SnmpAdminString,
    cfprEquipmentBreakOutCapProviderPolicyLevel                      Gauge32,
    cfprEquipmentBreakOutCapProviderPolicyOwner                      CfprPolicyPolicyOwner,
    cfprEquipmentBreakOutCapProviderMediaType                        CfprEquipmentMediaType,
    cfprEquipmentBreakOutCapProviderPortSpeedCap                     CfprEquipmentEthPortSpeedCap
}

cfprEquipmentBreakOutCapProviderInstanceId OBJECT-TYPE
    SYNTAX       CfprManagedObjectId
    MAX-ACCESS   not-accessible
    STATUS       current
    DESCRIPTION
        "Instance identifier of the managed object."
    ::= { cfprEquipmentBreakOutCapProviderEntry 1 }

cfprEquipmentBreakOutCapProviderDn OBJECT-TYPE
    SYNTAX       CfprManagedObjectDn
    MAX-ACCESS   read-only
    STATUS       current
    DESCRIPTION
        "Cisco Firepower equipment:BreakOutCapProvider:dn
        managed object property"
    ::= { cfprEquipmentBreakOutCapProviderEntry 2 }

cfprEquipmentBreakOutCapProviderRn OBJECT-TYPE
    SYNTAX       SnmpAdminString
    MAX-ACCESS   read-only
    STATUS       current
    DESCRIPTION
        "Cisco Firepower equipment:BreakOutCapProvider:rn
        managed object property"
    ::= { cfprEquipmentBreakOutCapProviderEntry 3 }

cfprEquipmentBreakOutCapProviderBreakoutSupported OBJECT-TYPE
    SYNTAX       TruthValue
    MAX-ACCESS   read-only
    STATUS       current
    DESCRIPTION
        "Cisco Firepower equipment:BreakOutCapProvider:breakoutSupported
        managed object property"
    ::= { cfprEquipmentBreakOutCapProviderEntry 4 }

cfprEquipmentBreakOutCapProviderDescr OBJECT-TYPE
    SYNTAX       SnmpAdminString
    MAX-ACCESS   read-only
    STATUS       current
    DESCRIPTION
        "Cisco Firepower equipment:BreakOutCapProvider:descr
        managed object property"
    ::= { cfprEquipmentBreakOutCapProviderEntry 5 }

cfprEquipmentBreakOutCapProviderIntId OBJECT-TYPE
    SYNTAX       SnmpAdminString
    MAX-ACCESS   read-only
    STATUS       current
    DESCRIPTION
        "Cisco Firepower equipment:BreakOutCapProvider:intId
        managed object property"
    ::= { cfprEquipmentBreakOutCapProviderEntry 6 }

cfprEquipmentBreakOutCapProviderName OBJECT-TYPE
    SYNTAX       SnmpAdminString
    MAX-ACCESS   read-only
    STATUS       current
    DESCRIPTION
        "Cisco Firepower equipment:BreakOutCapProvider:name
        managed object property"
    ::= { cfprEquipmentBreakOutCapProviderEntry 7 }

cfprEquipmentBreakOutCapProviderPolicyLevel OBJECT-TYPE
    SYNTAX       Gauge32
    MAX-ACCESS   read-only
    STATUS       current
    DESCRIPTION
        "Cisco Firepower equipment:BreakOutCapProvider:policyLevel
        managed object property"
    ::= { cfprEquipmentBreakOutCapProviderEntry 8 }

cfprEquipmentBreakOutCapProviderPolicyOwner OBJECT-TYPE
    SYNTAX       CfprPolicyPolicyOwner
    MAX-ACCESS   read-only
    STATUS       current
    DESCRIPTION
        "Cisco Firepower equipment:BreakOutCapProvider:policyOwner
        managed object property"
    ::= { cfprEquipmentBreakOutCapProviderEntry 9 }

cfprEquipmentBreakOutCapProviderMediaType OBJECT-TYPE
    SYNTAX       CfprEquipmentMediaType
    MAX-ACCESS   read-only
    STATUS       current
    DESCRIPTION
        "Cisco Firepower equipment:BreakOutCapProvider:mediaType
        managed object property"
    ::= { cfprEquipmentBreakOutCapProviderEntry 10 }

cfprEquipmentBreakOutCapProviderPortSpeedCap OBJECT-TYPE
    SYNTAX       CfprEquipmentEthPortSpeedCap
    MAX-ACCESS   read-only
    STATUS       current
    DESCRIPTION
        "Cisco Firepower equipment:BreakOutCapProvider:portSpeedCap
        managed object property"
    ::= { cfprEquipmentBreakOutCapProviderEntry 11 }

cfprEquipmentCapModSpecTable OBJECT-TYPE
    SYNTAX           SEQUENCE OF CfprEquipmentCapModSpecEntry
    MAX-ACCESS       not-accessible
    STATUS           current
    DESCRIPTION
        "Cisco Firepower equipment:CapModSpec managed object table"
    ::= { cfprEquipmentObjects 147 }

cfprEquipmentCapModSpecEntry OBJECT-TYPE
    SYNTAX           CfprEquipmentCapModSpecEntry
    MAX-ACCESS       not-accessible
    STATUS           current
    DESCRIPTION
        "Entry for the cfprEquipmentCapModSpecTable table."
    INDEX { cfprEquipmentCapModSpecInstanceId }
    ::= { cfprEquipmentCapModSpecTable 1 }

CfprEquipmentCapModSpecEntry ::= SEQUENCE {
    cfprEquipmentCapModSpecInstanceId                                CfprManagedObjectId,
    cfprEquipmentCapModSpecDn                                        CfprManagedObjectDn,
    cfprEquipmentCapModSpecRn                                        SnmpAdminString,
    cfprEquipmentCapModSpecPath                                      SnmpAdminString
}

cfprEquipmentCapModSpecInstanceId OBJECT-TYPE
    SYNTAX       CfprManagedObjectId
    MAX-ACCESS   not-accessible
    STATUS       current
    DESCRIPTION
        "Instance identifier of the managed object."
    ::= { cfprEquipmentCapModSpecEntry 1 }

cfprEquipmentCapModSpecDn OBJECT-TYPE
    SYNTAX       CfprManagedObjectDn
    MAX-ACCESS   read-only
    STATUS       current
    DESCRIPTION
        "Cisco Firepower equipment:CapModSpec:dn managed object property"
    ::= { cfprEquipmentCapModSpecEntry 2 }

cfprEquipmentCapModSpecRn OBJECT-TYPE
    SYNTAX       SnmpAdminString
    MAX-ACCESS   read-only
    STATUS       current
    DESCRIPTION
        "Cisco Firepower equipment:CapModSpec:rn managed object property"
    ::= { cfprEquipmentCapModSpecEntry 3 }

cfprEquipmentCapModSpecPath OBJECT-TYPE
    SYNTAX       SnmpAdminString
    MAX-ACCESS   read-only
    STATUS       current
    DESCRIPTION
        "Cisco Firepower equipment:CapModSpec:path managed
        object property"
    ::= { cfprEquipmentCapModSpecEntry 4 }

cfprEquipmentCatalogCapProviderTable OBJECT-TYPE
    SYNTAX           SEQUENCE OF CfprEquipmentCatalogCapProviderEntry
    MAX-ACCESS       not-accessible
    STATUS           current
    DESCRIPTION
        "Cisco Firepower equipment:CatalogCapProvider managed
        object table"
    ::= { cfprEquipmentObjects 20 }

cfprEquipmentCatalogCapProviderEntry OBJECT-TYPE
    SYNTAX           CfprEquipmentCatalogCapProviderEntry
    MAX-ACCESS       not-accessible
    STATUS           current
    DESCRIPTION
        "Entry for the cfprEquipmentCatalogCapProviderTable table."
    INDEX { cfprEquipmentCatalogCapProviderInstanceId }
    ::= { cfprEquipmentCatalogCapProviderTable 1 }

CfprEquipmentCatalogCapProviderEntry ::= SEQUENCE {
    cfprEquipmentCatalogCapProviderInstanceId                        CfprManagedObjectId,
    cfprEquipmentCatalogCapProviderDn                                CfprManagedObjectDn,
    cfprEquipmentCatalogCapProviderRn                                SnmpAdminString,
    cfprEquipmentCatalogCapProviderDeleted                           TruthValue,
    cfprEquipmentCatalogCapProviderDeprecated                        TruthValue,
    cfprEquipmentCatalogCapProviderElementLoadFailures               Gauge32,
    cfprEquipmentCatalogCapProviderElementsLoaded                    Gauge32,
    cfprEquipmentCatalogCapProviderGencount                          Gauge32,
    cfprEquipmentCatalogCapProviderLoadErrors                        Gauge32,
    cfprEquipmentCatalogCapProviderLoadWarnings                      Gauge32,
    cfprEquipmentCatalogCapProviderMgmtPlaneVer                      SnmpAdminString,
    cfprEquipmentCatalogCapProviderModel                             SnmpAdminString,
    cfprEquipmentCatalogCapProviderPromCardType                      Gauge32,
    cfprEquipmentCatalogCapProviderRevision                          SnmpAdminString,
    cfprEquipmentCatalogCapProviderVendor                            SnmpAdminString
}

cfprEquipmentCatalogCapProviderInstanceId OBJECT-TYPE
    SYNTAX       CfprManagedObjectId
    MAX-ACCESS   not-accessible
    STATUS       current
    DESCRIPTION
        "Instance identifier of the managed object."
    ::= { cfprEquipmentCatalogCapProviderEntry 1 }

cfprEquipmentCatalogCapProviderDn OBJECT-TYPE
    SYNTAX       CfprManagedObjectDn
    MAX-ACCESS   read-only
    STATUS       current
    DESCRIPTION
        "Cisco Firepower equipment:CatalogCapProvider:dn
        managed object property"
    ::= { cfprEquipmentCatalogCapProviderEntry 2 }

cfprEquipmentCatalogCapProviderRn OBJECT-TYPE
    SYNTAX       SnmpAdminString
    MAX-ACCESS   read-only
    STATUS       current
    DESCRIPTION
        "Cisco Firepower equipment:CatalogCapProvider:rn
        managed object property"
    ::= { cfprEquipmentCatalogCapProviderEntry 3 }

cfprEquipmentCatalogCapProviderDeleted OBJECT-TYPE
    SYNTAX       TruthValue
    MAX-ACCESS   read-only
    STATUS       current
    DESCRIPTION
        "Cisco Firepower equipment:CatalogCapProvider:deleted
        managed object property"
    ::= { cfprEquipmentCatalogCapProviderEntry 4 }

cfprEquipmentCatalogCapProviderDeprecated OBJECT-TYPE
    SYNTAX       TruthValue
    MAX-ACCESS   read-only
    STATUS       current
    DESCRIPTION
        "Cisco Firepower equipment:CatalogCapProvider:deprecated
        managed object property"
    ::= { cfprEquipmentCatalogCapProviderEntry 5 }

cfprEquipmentCatalogCapProviderElementLoadFailures OBJECT-TYPE
    SYNTAX       Gauge32
    MAX-ACCESS   read-only
    STATUS       current
    DESCRIPTION
        "Cisco Firepower equipment:CatalogCapProvider:elementLoadFailures
        managed object property"
    ::= { cfprEquipmentCatalogCapProviderEntry 6 }

cfprEquipmentCatalogCapProviderElementsLoaded OBJECT-TYPE
    SYNTAX       Gauge32
    MAX-ACCESS   read-only
    STATUS       current
    DESCRIPTION
        "Cisco Firepower equipment:CatalogCapProvider:elementsLoaded
        managed object property"
    ::= { cfprEquipmentCatalogCapProviderEntry 7 }

cfprEquipmentCatalogCapProviderGencount OBJECT-TYPE
    SYNTAX       Gauge32
    MAX-ACCESS   read-only
    STATUS       current
    DESCRIPTION
        "Cisco Firepower equipment:CatalogCapProvider:gencount
        managed object property"
    ::= { cfprEquipmentCatalogCapProviderEntry 8 }

cfprEquipmentCatalogCapProviderLoadErrors OBJECT-TYPE
    SYNTAX       Gauge32
    MAX-ACCESS   read-only
    STATUS       current
    DESCRIPTION
        "Cisco Firepower equipment:CatalogCapProvider:loadErrors
        managed object property"
    ::= { cfprEquipmentCatalogCapProviderEntry 9 }

cfprEquipmentCatalogCapProviderLoadWarnings OBJECT-TYPE
    SYNTAX       Gauge32
    MAX-ACCESS   read-only
    STATUS       current
    DESCRIPTION
        "Cisco Firepower equipment:CatalogCapProvider:loadWarnings
        managed object property"
    ::= { cfprEquipmentCatalogCapProviderEntry 10 }

cfprEquipmentCatalogCapProviderMgmtPlaneVer OBJECT-TYPE
    SYNTAX       SnmpAdminString
    MAX-ACCESS   read-only
    STATUS       current
    DESCRIPTION
        "Cisco Firepower equipment:CatalogCapProvider:mgmtPlaneVer
        managed object property"
    ::= { cfprEquipmentCatalogCapProviderEntry 11 }

cfprEquipmentCatalogCapProviderModel OBJECT-TYPE
    SYNTAX       SnmpAdminString
    MAX-ACCESS   read-only
    STATUS       current
    DESCRIPTION
        "Cisco Firepower equipment:CatalogCapProvider:model
        managed object property"
    ::= { cfprEquipmentCatalogCapProviderEntry 12 }

cfprEquipmentCatalogCapProviderPromCardType OBJECT-TYPE
    SYNTAX       Gauge32
    MAX-ACCESS   read-only
    STATUS       current
    DESCRIPTION
        "Cisco Firepower equipment:CatalogCapProvider:promCardType
        managed object property"
    ::= { cfprEquipmentCatalogCapProviderEntry 13 }

cfprEquipmentCatalogCapProviderRevision OBJECT-TYPE
    SYNTAX       SnmpAdminString
    MAX-ACCESS   read-only
    STATUS       current
    DESCRIPTION
        "Cisco Firepower equipment:CatalogCapProvider:revision
        managed object property"
    ::= { cfprEquipmentCatalogCapProviderEntry 14 }

cfprEquipmentCatalogCapProviderVendor OBJECT-TYPE
    SYNTAX       SnmpAdminString
    MAX-ACCESS   read-only
    STATUS       current
    DESCRIPTION
        "Cisco Firepower equipment:CatalogCapProvider:vendor
        managed object property"
    ::= { cfprEquipmentCatalogCapProviderEntry 15 }

cfprEquipmentChPowerTable OBJECT-TYPE
    SYNTAX           SEQUENCE OF CfprEquipmentChPowerEntry
    MAX-ACCESS       not-accessible
    STATUS           current
    DESCRIPTION
        "Cisco Firepower equipment:ChPower managed object table"
    ::= { cfprEquipmentObjects 148 }

cfprEquipmentChPowerEntry OBJECT-TYPE
    SYNTAX           CfprEquipmentChPowerEntry
    MAX-ACCESS       not-accessible
    STATUS           current
    DESCRIPTION
        "Entry for the cfprEquipmentChPowerTable table."
    INDEX { cfprEquipmentChPowerInstanceId }
    ::= { cfprEquipmentChPowerTable 1 }

CfprEquipmentChPowerEntry ::= SEQUENCE {
    cfprEquipmentChPowerInstanceId                                   CfprManagedObjectId,
    cfprEquipmentChPowerDn                                           CfprManagedObjectDn,
    cfprEquipmentChPowerRn                                           SnmpAdminString,
    cfprEquipmentChPowerAction                                       CfprEquipmentShutdownAction,
    cfprEquipmentChPowerMask                                         BITS,
    cfprEquipmentChPowerReason                                       SnmpAdminString
}

cfprEquipmentChPowerInstanceId OBJECT-TYPE
    SYNTAX       CfprManagedObjectId
    MAX-ACCESS   not-accessible
    STATUS       current
    DESCRIPTION
        "Instance identifier of the managed object."
    ::= { cfprEquipmentChPowerEntry 1 }

cfprEquipmentChPowerDn OBJECT-TYPE
    SYNTAX       CfprManagedObjectDn
    MAX-ACCESS   read-only
    STATUS       current
    DESCRIPTION
        "Cisco Firepower equipment:ChPower:dn managed object property"
    ::= { cfprEquipmentChPowerEntry 2 }

cfprEquipmentChPowerRn OBJECT-TYPE
    SYNTAX       SnmpAdminString
    MAX-ACCESS   read-only
    STATUS       current
    DESCRIPTION
        "Cisco Firepower equipment:ChPower:rn managed object property"
    ::= { cfprEquipmentChPowerEntry 3 }

cfprEquipmentChPowerAction OBJECT-TYPE
    SYNTAX       CfprEquipmentShutdownAction
    MAX-ACCESS   read-only
    STATUS       current
    DESCRIPTION
        "Cisco Firepower equipment:ChPower:action managed object property"
    ::= { cfprEquipmentChPowerEntry 4 }

cfprEquipmentChPowerMask OBJECT-TYPE
    SYNTAX       BITS
    MAX-ACCESS   read-only
    STATUS       current
    DESCRIPTION
        "Cisco Firepower equipment:ChPower:mask managed object property"
    ::= { cfprEquipmentChPowerEntry 5 }

cfprEquipmentChPowerReason OBJECT-TYPE
    SYNTAX       SnmpAdminString
    MAX-ACCESS   read-only
    STATUS       current
    DESCRIPTION
        "Cisco Firepower equipment:ChPower:reason managed object property"
    ::= { cfprEquipmentChPowerEntry 6 }

cfprEquipmentChassisTable OBJECT-TYPE
    SYNTAX           SEQUENCE OF CfprEquipmentChassisEntry
    MAX-ACCESS       not-accessible
    STATUS           current
    DESCRIPTION
        "Cisco Firepower equipment:Chassis managed object table"
    ::= { cfprEquipmentObjects 21 }

cfprEquipmentChassisEntry OBJECT-TYPE
    SYNTAX           CfprEquipmentChassisEntry
    MAX-ACCESS       not-accessible
    STATUS           current
    DESCRIPTION
        "Entry for the cfprEquipmentChassisTable table."
    INDEX { cfprEquipmentChassisInstanceId }
    ::= { cfprEquipmentChassisTable 1 }

CfprEquipmentChassisEntry ::= SEQUENCE {
    cfprEquipmentChassisInstanceId                                   CfprManagedObjectId,
    cfprEquipmentChassisDn                                           CfprManagedObjectDn,
    cfprEquipmentChassisRn                                           SnmpAdminString,
    cfprEquipmentChassisAckProgressIndicator                         CfprEquipmentChassisConfigProgressIndicator,
    cfprEquipmentChassisAdminState                                   CfprEquipmentChassisAdminState,
    cfprEquipmentChassisConfigState                                  CfprEquipmentChassisConfigState,
    cfprEquipmentChassisConnPath                                     CfprEquipmentConnectionStatus,
    cfprEquipmentChassisConnStatus                                   CfprEquipmentConnectionStatus,
    cfprEquipmentChassisFabricEpDn                                   SnmpAdminString,
    cfprEquipmentChassisFltAggr                                      Unsigned64,
    cfprEquipmentChassisFsmDescr                                     SnmpAdminString,
    cfprEquipmentChassisFsmPrev                                      SnmpAdminString,
    cfprEquipmentChassisFsmProgr                                     Gauge32,
    cfprEquipmentChassisFsmRmtInvErrCode                             Gauge32,
    cfprEquipmentChassisFsmRmtInvErrDescr                            SnmpAdminString,
    cfprEquipmentChassisFsmRmtInvRslt                                CfprConditionRemoteInvRslt,
    cfprEquipmentChassisFsmStageDescr                                SnmpAdminString,
    cfprEquipmentChassisFsmStamp                                     DateAndTime,
    cfprEquipmentChassisFsmStatus                                    SnmpAdminString,
    cfprEquipmentChassisFsmTry                                       Gauge32,
    cfprEquipmentChassisId                                           CfprEquipmentChassisId,
    cfprEquipmentChassisLcTs                                         DateAndTime,
    cfprEquipmentChassisLicGP                                        Unsigned64,
    cfprEquipmentChassisLicState                                     CfprLicenseState,
    cfprEquipmentChassisManagingInst                                 CfprNetworkSwitchId,
    cfprEquipmentChassisMfgTime                                      DateAndTime,
    cfprEquipmentChassisModel                                        SnmpAdminString,
    cfprEquipmentChassisOperQualifier                                CfprEquipmentChassisIssues,
    cfprEquipmentChassisOperQualifierReason                          SnmpAdminString,
    cfprEquipmentChassisOperState                                    CfprEquipmentOperability,
    cfprEquipmentChassisOperability                                  CfprEquipmentOperability,
    cfprEquipmentChassisPartNumber                                   SnmpAdminString,
    cfprEquipmentChassisPower                                        CfprEquipmentChassisPowerOperState,
    cfprEquipmentChassisPresence                                     CfprEquipmentPresence,
    cfprEquipmentChassisRevision                                     SnmpAdminString,
    cfprEquipmentChassisSeepromOperState                             CfprEquipmentOperability,
    cfprEquipmentChassisSerial                                       SnmpAdminString,
    cfprEquipmentChassisThermal                                      CfprEquipmentSensorThresholdStatus,
    cfprEquipmentChassisThermalStateQualifier                        SnmpAdminString,
    cfprEquipmentChassisUsrLbl                                       SnmpAdminString,
    cfprEquipmentChassisVendor                                       SnmpAdminString,
    cfprEquipmentChassisVersionHolder                                TruthValue,
    cfprEquipmentChassisVid                                          SnmpAdminString,
    cfprEquipmentChassisFsmFlags                                     SnmpAdminString,
    cfprEquipmentChassisIsDevKeyEnabledOnChassis                     TruthValue
}

cfprEquipmentChassisInstanceId OBJECT-TYPE
    SYNTAX       CfprManagedObjectId
    MAX-ACCESS   not-accessible
    STATUS       current
    DESCRIPTION
        "Instance identifier of the managed object."
    ::= { cfprEquipmentChassisEntry 1 }

cfprEquipmentChassisDn OBJECT-TYPE
    SYNTAX       CfprManagedObjectDn
    MAX-ACCESS   read-only
    STATUS       current
    DESCRIPTION
        "Cisco Firepower equipment:Chassis:dn managed object property"
    ::= { cfprEquipmentChassisEntry 2 }

cfprEquipmentChassisRn OBJECT-TYPE
    SYNTAX       SnmpAdminString
    MAX-ACCESS   read-only
    STATUS       current
    DESCRIPTION
        "Cisco Firepower equipment:Chassis:rn managed object property"
    ::= { cfprEquipmentChassisEntry 3 }

cfprEquipmentChassisAckProgressIndicator OBJECT-TYPE
    SYNTAX       CfprEquipmentChassisConfigProgressIndicator
    MAX-ACCESS   read-only
    STATUS       current
    DESCRIPTION
        "Cisco Firepower equipment:Chassis:ackProgressIndicator
        managed object property"
    ::= { cfprEquipmentChassisEntry 4 }

cfprEquipmentChassisAdminState OBJECT-TYPE
    SYNTAX       CfprEquipmentChassisAdminState
    MAX-ACCESS   read-only
    STATUS       current
    DESCRIPTION
        "Cisco Firepower equipment:Chassis:adminState managed
        object property"
    ::= { cfprEquipmentChassisEntry 5 }

cfprEquipmentChassisConfigState OBJECT-TYPE
    SYNTAX       CfprEquipmentChassisConfigState
    MAX-ACCESS   read-only
    STATUS       current
    DESCRIPTION
        "Cisco Firepower equipment:Chassis:configState
        managed object property"
    ::= { cfprEquipmentChassisEntry 6 }

cfprEquipmentChassisConnPath OBJECT-TYPE
    SYNTAX       CfprEquipmentConnectionStatus
    MAX-ACCESS   read-only
    STATUS       current
    DESCRIPTION
        "Cisco Firepower equipment:Chassis:connPath managed
        object property"
    ::= { cfprEquipmentChassisEntry 7 }

cfprEquipmentChassisConnStatus OBJECT-TYPE
    SYNTAX       CfprEquipmentConnectionStatus
    MAX-ACCESS   read-only
    STATUS       current
    DESCRIPTION
        "Cisco Firepower equipment:Chassis:connStatus managed
        object property"
    ::= { cfprEquipmentChassisEntry 8 }

cfprEquipmentChassisFabricEpDn OBJECT-TYPE
    SYNTAX       SnmpAdminString
    MAX-ACCESS   read-only
    STATUS       current
    DESCRIPTION
        "Cisco Firepower equipment:Chassis:fabricEpDn managed
        object property"
    ::= { cfprEquipmentChassisEntry 9 }

cfprEquipmentChassisFltAggr OBJECT-TYPE
    SYNTAX       Unsigned64
    MAX-ACCESS   read-only
    STATUS       current
    DESCRIPTION
        "Cisco Firepower equipment:Chassis:fltAggr managed
        object property"
    ::= { cfprEquipmentChassisEntry 10 }

cfprEquipmentChassisFsmDescr OBJECT-TYPE
    SYNTAX       SnmpAdminString
    MAX-ACCESS   read-only
    STATUS       current
    DESCRIPTION
        "Cisco Firepower equipment:Chassis:fsmDescr managed
        object property"
    ::= { cfprEquipmentChassisEntry 11 }

cfprEquipmentChassisFsmPrev OBJECT-TYPE
    SYNTAX       SnmpAdminString
    MAX-ACCESS   read-only
    STATUS       current
    DESCRIPTION
        "Cisco Firepower equipment:Chassis:fsmPrev managed
        object property"
    ::= { cfprEquipmentChassisEntry 12 }

cfprEquipmentChassisFsmProgr OBJECT-TYPE
    SYNTAX       Gauge32
    MAX-ACCESS   read-only
    STATUS       current
    DESCRIPTION
        "Cisco Firepower equipment:Chassis:fsmProgr managed
        object property"
    ::= { cfprEquipmentChassisEntry 13 }

cfprEquipmentChassisFsmRmtInvErrCode OBJECT-TYPE
    SYNTAX       Gauge32
    MAX-ACCESS   read-only
    STATUS       current
    DESCRIPTION
        "Cisco Firepower equipment:Chassis:fsmRmtInvErrCode
        managed object property"
    ::= { cfprEquipmentChassisEntry 14 }

cfprEquipmentChassisFsmRmtInvErrDescr OBJECT-TYPE
    SYNTAX       SnmpAdminString
    MAX-ACCESS   read-only
    STATUS       current
    DESCRIPTION
        "Cisco Firepower equipment:Chassis:fsmRmtInvErrDescr
        managed object property"
    ::= { cfprEquipmentChassisEntry 15 }

cfprEquipmentChassisFsmRmtInvRslt OBJECT-TYPE
    SYNTAX       CfprConditionRemoteInvRslt
    MAX-ACCESS   read-only
    STATUS       current
    DESCRIPTION
        "Cisco Firepower equipment:Chassis:fsmRmtInvRslt
        managed object property"
    ::= { cfprEquipmentChassisEntry 16 }

cfprEquipmentChassisFsmStageDescr OBJECT-TYPE
    SYNTAX       SnmpAdminString
    MAX-ACCESS   read-only
    STATUS       current
    DESCRIPTION
        "Cisco Firepower equipment:Chassis:fsmStageDescr
        managed object property"
    ::= { cfprEquipmentChassisEntry 17 }

cfprEquipmentChassisFsmStamp OBJECT-TYPE
    SYNTAX       DateAndTime
    MAX-ACCESS   read-only
    STATUS       current
    DESCRIPTION
        "Cisco Firepower equipment:Chassis:fsmStamp managed
        object property"
    ::= { cfprEquipmentChassisEntry 18 }

cfprEquipmentChassisFsmStatus OBJECT-TYPE
    SYNTAX       SnmpAdminString
    MAX-ACCESS   read-only
    STATUS       current
    DESCRIPTION
        "Cisco Firepower equipment:Chassis:fsmStatus managed
        object property"
    ::= { cfprEquipmentChassisEntry 19 }

cfprEquipmentChassisFsmTry OBJECT-TYPE
    SYNTAX       Gauge32
    MAX-ACCESS   read-only
    STATUS       current
    DESCRIPTION
        "Cisco Firepower equipment:Chassis:fsmTry managed object property"
    ::= { cfprEquipmentChassisEntry 20 }

cfprEquipmentChassisId OBJECT-TYPE
    SYNTAX       CfprEquipmentChassisId
    MAX-ACCESS   read-only
    STATUS       current
    DESCRIPTION
        "Cisco Firepower equipment:Chassis:id managed object property"
    ::= { cfprEquipmentChassisEntry 21 }

cfprEquipmentChassisLcTs OBJECT-TYPE
    SYNTAX       DateAndTime
    MAX-ACCESS   read-only
    STATUS       current
    DESCRIPTION
        "Cisco Firepower equipment:Chassis:lcTs managed object property"
    ::= { cfprEquipmentChassisEntry 22 }

cfprEquipmentChassisLicGP OBJECT-TYPE
    SYNTAX       Unsigned64
    MAX-ACCESS   read-only
    STATUS       current
    DESCRIPTION
        "Cisco Firepower equipment:Chassis:licGP managed object property"
    ::= { cfprEquipmentChassisEntry 23 }

cfprEquipmentChassisLicState OBJECT-TYPE
    SYNTAX       CfprLicenseState
    MAX-ACCESS   read-only
    STATUS       current
    DESCRIPTION
        "Cisco Firepower equipment:Chassis:licState managed
        object property"
    ::= { cfprEquipmentChassisEntry 24 }

cfprEquipmentChassisManagingInst OBJECT-TYPE
    SYNTAX       CfprNetworkSwitchId
    MAX-ACCESS   read-only
    STATUS       current
    DESCRIPTION
        "Cisco Firepower equipment:Chassis:managingInst
        managed object property"
    ::= { cfprEquipmentChassisEntry 25 }

cfprEquipmentChassisMfgTime OBJECT-TYPE
    SYNTAX       DateAndTime
    MAX-ACCESS   read-only
    STATUS       current
    DESCRIPTION
        "Cisco Firepower equipment:Chassis:mfgTime managed
        object property"
    ::= { cfprEquipmentChassisEntry 26 }

cfprEquipmentChassisModel OBJECT-TYPE
    SYNTAX       SnmpAdminString
    MAX-ACCESS   read-only
    STATUS       current
    DESCRIPTION
        "Cisco Firepower equipment:Chassis:model managed object property"
    ::= { cfprEquipmentChassisEntry 27 }

cfprEquipmentChassisOperQualifier OBJECT-TYPE
    SYNTAX       CfprEquipmentChassisIssues
    MAX-ACCESS   read-only
    STATUS       current
    DESCRIPTION
        "Cisco Firepower equipment:Chassis:operQualifier
        managed object property"
    ::= { cfprEquipmentChassisEntry 28 }

cfprEquipmentChassisOperQualifierReason OBJECT-TYPE
    SYNTAX       SnmpAdminString
    MAX-ACCESS   read-only
    STATUS       current
    DESCRIPTION
        "Cisco Firepower equipment:Chassis:operQualifierReason
        managed object property"
    ::= { cfprEquipmentChassisEntry 29 }

cfprEquipmentChassisOperState OBJECT-TYPE
    SYNTAX       CfprEquipmentOperability
    MAX-ACCESS   read-only
    STATUS       current
    DESCRIPTION
        "Cisco Firepower equipment:Chassis:operState managed
        object property"
    ::= { cfprEquipmentChassisEntry 30 }

cfprEquipmentChassisOperability OBJECT-TYPE
    SYNTAX       CfprEquipmentOperability
    MAX-ACCESS   read-only
    STATUS       current
    DESCRIPTION
        "Cisco Firepower equipment:Chassis:operability
        managed object property"
    ::= { cfprEquipmentChassisEntry 31 }

cfprEquipmentChassisPartNumber OBJECT-TYPE
    SYNTAX       SnmpAdminString
    MAX-ACCESS   read-only
    STATUS       current
    DESCRIPTION
        "Cisco Firepower equipment:Chassis:partNumber managed
        object property"
    ::= { cfprEquipmentChassisEntry 32 }

cfprEquipmentChassisPower OBJECT-TYPE
    SYNTAX       CfprEquipmentChassisPowerOperState
    MAX-ACCESS   read-only
    STATUS       current
    DESCRIPTION
        "Cisco Firepower equipment:Chassis:power managed object property"
    ::= { cfprEquipmentChassisEntry 33 }

cfprEquipmentChassisPresence OBJECT-TYPE
    SYNTAX       CfprEquipmentPresence
    MAX-ACCESS   read-only
    STATUS       current
    DESCRIPTION
        "Cisco Firepower equipment:Chassis:presence managed
        object property"
    ::= { cfprEquipmentChassisEntry 34 }

cfprEquipmentChassisRevision OBJECT-TYPE
    SYNTAX       SnmpAdminString
    MAX-ACCESS   read-only
    STATUS       current
    DESCRIPTION
        "Cisco Firepower equipment:Chassis:revision managed
        object property"
    ::= { cfprEquipmentChassisEntry 35 }

cfprEquipmentChassisSeepromOperState OBJECT-TYPE
    SYNTAX       CfprEquipmentOperability
    MAX-ACCESS   read-only
    STATUS       current
    DESCRIPTION
        "Cisco Firepower equipment:Chassis:seepromOperState
        managed object property"
    ::= { cfprEquipmentChassisEntry 36 }

cfprEquipmentChassisSerial OBJECT-TYPE
    SYNTAX       SnmpAdminString
    MAX-ACCESS   read-only
    STATUS       current
    DESCRIPTION
        "Cisco Firepower equipment:Chassis:serial managed object property"
    ::= { cfprEquipmentChassisEntry 37 }

cfprEquipmentChassisThermal OBJECT-TYPE
    SYNTAX       CfprEquipmentSensorThresholdStatus
    MAX-ACCESS   read-only
    STATUS       current
    DESCRIPTION
        "Cisco Firepower equipment:Chassis:thermal managed
        object property"
    ::= { cfprEquipmentChassisEntry 38 }

cfprEquipmentChassisThermalStateQualifier OBJECT-TYPE
    SYNTAX       SnmpAdminString
    MAX-ACCESS   read-only
    STATUS       current
    DESCRIPTION
        "Cisco Firepower equipment:Chassis:thermalStateQualifier
        managed object property"
    ::= { cfprEquipmentChassisEntry 39 }

cfprEquipmentChassisUsrLbl OBJECT-TYPE
    SYNTAX       SnmpAdminString
    MAX-ACCESS   read-only
    STATUS       current
    DESCRIPTION
        "Cisco Firepower equipment:Chassis:usrLbl managed object property"
    ::= { cfprEquipmentChassisEntry 40 }

cfprEquipmentChassisVendor OBJECT-TYPE
    SYNTAX       SnmpAdminString
    MAX-ACCESS   read-only
    STATUS       current
    DESCRIPTION
        "Cisco Firepower equipment:Chassis:vendor managed object property"
    ::= { cfprEquipmentChassisEntry 41 }

cfprEquipmentChassisVersionHolder OBJECT-TYPE
    SYNTAX       TruthValue
    MAX-ACCESS   read-only
    STATUS       current
    DESCRIPTION
        "Cisco Firepower equipment:Chassis:versionHolder
        managed object property"
    ::= { cfprEquipmentChassisEntry 42 }

cfprEquipmentChassisVid OBJECT-TYPE
    SYNTAX       SnmpAdminString
    MAX-ACCESS   read-only
    STATUS       current
    DESCRIPTION
        "Cisco Firepower equipment:Chassis:vid managed object property"
    ::= { cfprEquipmentChassisEntry 43 }

cfprEquipmentChassisFsmFlags OBJECT-TYPE
    SYNTAX       SnmpAdminString
    MAX-ACCESS   read-only
    STATUS       current
    DESCRIPTION
        "Cisco Firepower equipment:Chassis:fsmFlags managed
        object property"
    ::= { cfprEquipmentChassisEntry 44 }

cfprEquipmentChassisIsDevKeyEnabledOnChassis OBJECT-TYPE
    SYNTAX       TruthValue
    MAX-ACCESS   read-only
    STATUS       current
    DESCRIPTION
        "Cisco Firepower equipment:Chassis:isDevKeyEnabledOnChassis
        managed object property"
    ::= { cfprEquipmentChassisEntry 45 }

cfprEquipmentChassisCapProviderTable OBJECT-TYPE
    SYNTAX           SEQUENCE OF CfprEquipmentChassisCapProviderEntry
    MAX-ACCESS       not-accessible
    STATUS           current
    DESCRIPTION
        "Cisco Firepower equipment:ChassisCapProvider managed
        object table"
    ::= { cfprEquipmentObjects 22 }

cfprEquipmentChassisCapProviderEntry OBJECT-TYPE
    SYNTAX           CfprEquipmentChassisCapProviderEntry
    MAX-ACCESS       not-accessible
    STATUS           current
    DESCRIPTION
        "Entry for the cfprEquipmentChassisCapProviderTable table."
    INDEX { cfprEquipmentChassisCapProviderInstanceId }
    ::= { cfprEquipmentChassisCapProviderTable 1 }

CfprEquipmentChassisCapProviderEntry ::= SEQUENCE {
    cfprEquipmentChassisCapProviderInstanceId                        CfprManagedObjectId,
    cfprEquipmentChassisCapProviderDn                                CfprManagedObjectDn,
    cfprEquipmentChassisCapProviderRn                                SnmpAdminString,
    cfprEquipmentChassisCapProviderDeleted                           TruthValue,
    cfprEquipmentChassisCapProviderDeprecated                        TruthValue,
    cfprEquipmentChassisCapProviderElementLoadFailures               Gauge32,
    cfprEquipmentChassisCapProviderElementsLoaded                    Gauge32,
    cfprEquipmentChassisCapProviderGencount                          Gauge32,
    cfprEquipmentChassisCapProviderLoadErrors                        Gauge32,
    cfprEquipmentChassisCapProviderLoadWarnings                      Gauge32,
    cfprEquipmentChassisCapProviderMgmtPlaneVer                      SnmpAdminString,
    cfprEquipmentChassisCapProviderModel                             SnmpAdminString,
    cfprEquipmentChassisCapProviderPromCardType                      Gauge32,
    cfprEquipmentChassisCapProviderRevision                          SnmpAdminString,
    cfprEquipmentChassisCapProviderVendor                            SnmpAdminString
}

cfprEquipmentChassisCapProviderInstanceId OBJECT-TYPE
    SYNTAX       CfprManagedObjectId
    MAX-ACCESS   not-accessible
    STATUS       current
    DESCRIPTION
        "Instance identifier of the managed object."
    ::= { cfprEquipmentChassisCapProviderEntry 1 }

cfprEquipmentChassisCapProviderDn OBJECT-TYPE
    SYNTAX       CfprManagedObjectDn
    MAX-ACCESS   read-only
    STATUS       current
    DESCRIPTION
        "Cisco Firepower equipment:ChassisCapProvider:dn
        managed object property"
    ::= { cfprEquipmentChassisCapProviderEntry 2 }

cfprEquipmentChassisCapProviderRn OBJECT-TYPE
    SYNTAX       SnmpAdminString
    MAX-ACCESS   read-only
    STATUS       current
    DESCRIPTION
        "Cisco Firepower equipment:ChassisCapProvider:rn
        managed object property"
    ::= { cfprEquipmentChassisCapProviderEntry 3 }

cfprEquipmentChassisCapProviderDeleted OBJECT-TYPE
    SYNTAX       TruthValue
    MAX-ACCESS   read-only
    STATUS       current
    DESCRIPTION
        "Cisco Firepower equipment:ChassisCapProvider:deleted
        managed object property"
    ::= { cfprEquipmentChassisCapProviderEntry 4 }

cfprEquipmentChassisCapProviderDeprecated OBJECT-TYPE
    SYNTAX       TruthValue
    MAX-ACCESS   read-only
    STATUS       current
    DESCRIPTION
        "Cisco Firepower equipment:ChassisCapProvider:deprecated
        managed object property"
    ::= { cfprEquipmentChassisCapProviderEntry 5 }

cfprEquipmentChassisCapProviderElementLoadFailures OBJECT-TYPE
    SYNTAX       Gauge32
    MAX-ACCESS   read-only
    STATUS       current
    DESCRIPTION
        "Cisco Firepower equipment:ChassisCapProvider:elementLoadFailures
        managed object property"
    ::= { cfprEquipmentChassisCapProviderEntry 6 }

cfprEquipmentChassisCapProviderElementsLoaded OBJECT-TYPE
    SYNTAX       Gauge32
    MAX-ACCESS   read-only
    STATUS       current
    DESCRIPTION
        "Cisco Firepower equipment:ChassisCapProvider:elementsLoaded
        managed object property"
    ::= { cfprEquipmentChassisCapProviderEntry 7 }

cfprEquipmentChassisCapProviderGencount OBJECT-TYPE
    SYNTAX       Gauge32
    MAX-ACCESS   read-only
    STATUS       current
    DESCRIPTION
        "Cisco Firepower equipment:ChassisCapProvider:gencount
        managed object property"
    ::= { cfprEquipmentChassisCapProviderEntry 8 }

cfprEquipmentChassisCapProviderLoadErrors OBJECT-TYPE
    SYNTAX       Gauge32
    MAX-ACCESS   read-only
    STATUS       current
    DESCRIPTION
        "Cisco Firepower equipment:ChassisCapProvider:loadErrors
        managed object property"
    ::= { cfprEquipmentChassisCapProviderEntry 9 }

cfprEquipmentChassisCapProviderLoadWarnings OBJECT-TYPE
    SYNTAX       Gauge32
    MAX-ACCESS   read-only
    STATUS       current
    DESCRIPTION
        "Cisco Firepower equipment:ChassisCapProvider:loadWarnings
        managed object property"
    ::= { cfprEquipmentChassisCapProviderEntry 10 }

cfprEquipmentChassisCapProviderMgmtPlaneVer OBJECT-TYPE
    SYNTAX       SnmpAdminString
    MAX-ACCESS   read-only
    STATUS       current
    DESCRIPTION
        "Cisco Firepower equipment:ChassisCapProvider:mgmtPlaneVer
        managed object property"
    ::= { cfprEquipmentChassisCapProviderEntry 11 }

cfprEquipmentChassisCapProviderModel OBJECT-TYPE
    SYNTAX       SnmpAdminString
    MAX-ACCESS   read-only
    STATUS       current
    DESCRIPTION
        "Cisco Firepower equipment:ChassisCapProvider:model
        managed object property"
    ::= { cfprEquipmentChassisCapProviderEntry 12 }

cfprEquipmentChassisCapProviderPromCardType OBJECT-TYPE
    SYNTAX       Gauge32
    MAX-ACCESS   read-only
    STATUS       current
    DESCRIPTION
        "Cisco Firepower equipment:ChassisCapProvider:promCardType
        managed object property"
    ::= { cfprEquipmentChassisCapProviderEntry 13 }

cfprEquipmentChassisCapProviderRevision OBJECT-TYPE
    SYNTAX       SnmpAdminString
    MAX-ACCESS   read-only
    STATUS       current
    DESCRIPTION
        "Cisco Firepower equipment:ChassisCapProvider:revision
        managed object property"
    ::= { cfprEquipmentChassisCapProviderEntry 14 }

cfprEquipmentChassisCapProviderVendor OBJECT-TYPE
    SYNTAX       SnmpAdminString
    MAX-ACCESS   read-only
    STATUS       current
    DESCRIPTION
        "Cisco Firepower equipment:ChassisCapProvider:vendor
        managed object property"
    ::= { cfprEquipmentChassisCapProviderEntry 15 }

cfprEquipmentChassisEnvTable OBJECT-TYPE
    SYNTAX           SEQUENCE OF CfprEquipmentChassisEnvEntry
    MAX-ACCESS       not-accessible
    STATUS           current
    DESCRIPTION
        "Cisco Firepower equipment:ChassisEnv managed object table"
    ::= { cfprEquipmentObjects 149 }

cfprEquipmentChassisEnvEntry OBJECT-TYPE
    SYNTAX           CfprEquipmentChassisEnvEntry
    MAX-ACCESS       not-accessible
    STATUS           current
    DESCRIPTION
        "Entry for the cfprEquipmentChassisEnvTable table."
    INDEX { cfprEquipmentChassisEnvInstanceId }
    ::= { cfprEquipmentChassisEnvTable 1 }

CfprEquipmentChassisEnvEntry ::= SEQUENCE {
    cfprEquipmentChassisEnvInstanceId                                CfprManagedObjectId,
    cfprEquipmentChassisEnvDn                                        CfprManagedObjectDn,
    cfprEquipmentChassisEnvRn                                        SnmpAdminString,
    cfprEquipmentChassisEnvCpuTemp                                   INTEGER,
    cfprEquipmentChassisEnvInletTemp                                 INTEGER,
    cfprEquipmentChassisEnvLastUpdatetime                            DateAndTime,
    cfprEquipmentChassisEnvModel                                     SnmpAdminString,
    cfprEquipmentChassisEnvRevision                                  SnmpAdminString,
    cfprEquipmentChassisEnvSerial                                    SnmpAdminString,
    cfprEquipmentChassisEnvTotalPower                                INTEGER,
    cfprEquipmentChassisEnvVendor                                    SnmpAdminString
}

cfprEquipmentChassisEnvInstanceId OBJECT-TYPE
    SYNTAX       CfprManagedObjectId
    MAX-ACCESS   not-accessible
    STATUS       current
    DESCRIPTION
        "Instance identifier of the managed object."
    ::= { cfprEquipmentChassisEnvEntry 1 }

cfprEquipmentChassisEnvDn OBJECT-TYPE
    SYNTAX       CfprManagedObjectDn
    MAX-ACCESS   read-only
    STATUS       current
    DESCRIPTION
        "Cisco Firepower equipment:ChassisEnv:dn managed object property"
    ::= { cfprEquipmentChassisEnvEntry 2 }

cfprEquipmentChassisEnvRn OBJECT-TYPE
    SYNTAX       SnmpAdminString
    MAX-ACCESS   read-only
    STATUS       current
    DESCRIPTION
        "Cisco Firepower equipment:ChassisEnv:rn managed object property"
    ::= { cfprEquipmentChassisEnvEntry 3 }

cfprEquipmentChassisEnvCpuTemp OBJECT-TYPE
    SYNTAX       INTEGER
    MAX-ACCESS   read-only
    STATUS       current
    DESCRIPTION
        "Cisco Firepower equipment:ChassisEnv:cpuTemp managed
        object property"
    ::= { cfprEquipmentChassisEnvEntry 4 }

cfprEquipmentChassisEnvInletTemp OBJECT-TYPE
    SYNTAX       INTEGER
    MAX-ACCESS   read-only
    STATUS       current
    DESCRIPTION
        "Cisco Firepower equipment:ChassisEnv:inletTemp
        managed object property"
    ::= { cfprEquipmentChassisEnvEntry 5 }

cfprEquipmentChassisEnvLastUpdatetime OBJECT-TYPE
    SYNTAX       DateAndTime
    MAX-ACCESS   read-only
    STATUS       current
    DESCRIPTION
        "Cisco Firepower equipment:ChassisEnv:lastUpdatetime
        managed object property"
    ::= { cfprEquipmentChassisEnvEntry 6 }

cfprEquipmentChassisEnvModel OBJECT-TYPE
    SYNTAX       SnmpAdminString
    MAX-ACCESS   read-only
    STATUS       current
    DESCRIPTION
        "Cisco Firepower equipment:ChassisEnv:model managed
        object property"
    ::= { cfprEquipmentChassisEnvEntry 7 }

cfprEquipmentChassisEnvRevision OBJECT-TYPE
    SYNTAX       SnmpAdminString
    MAX-ACCESS   read-only
    STATUS       current
    DESCRIPTION
        "Cisco Firepower equipment:ChassisEnv:revision
        managed object property"
    ::= { cfprEquipmentChassisEnvEntry 8 }

cfprEquipmentChassisEnvSerial OBJECT-TYPE
    SYNTAX       SnmpAdminString
    MAX-ACCESS   read-only
    STATUS       current
    DESCRIPTION
        "Cisco Firepower equipment:ChassisEnv:serial managed
        object property"
    ::= { cfprEquipmentChassisEnvEntry 9 }

cfprEquipmentChassisEnvTotalPower OBJECT-TYPE
    SYNTAX       INTEGER
    MAX-ACCESS   read-only
    STATUS       current
    DESCRIPTION
        "Cisco Firepower equipment:ChassisEnv:totalPower
        managed object property"
    ::= { cfprEquipmentChassisEnvEntry 10 }

cfprEquipmentChassisEnvVendor OBJECT-TYPE
    SYNTAX       SnmpAdminString
    MAX-ACCESS   read-only
    STATUS       current
    DESCRIPTION
        "Cisco Firepower equipment:ChassisEnv:vendor managed
        object property"
    ::= { cfprEquipmentChassisEnvEntry 11 }

cfprEquipmentChassisFsmTable OBJECT-TYPE
    SYNTAX           SEQUENCE OF CfprEquipmentChassisFsmEntry
    MAX-ACCESS       not-accessible
    STATUS           current
    DESCRIPTION
        "Cisco Firepower equipment:ChassisFsm managed object table"
    ::= { cfprEquipmentObjects 23 }

cfprEquipmentChassisFsmEntry OBJECT-TYPE
    SYNTAX           CfprEquipmentChassisFsmEntry
    MAX-ACCESS       not-accessible
    STATUS           current
    DESCRIPTION
        "Entry for the cfprEquipmentChassisFsmTable table."
    INDEX { cfprEquipmentChassisFsmInstanceId }
    ::= { cfprEquipmentChassisFsmTable 1 }

CfprEquipmentChassisFsmEntry ::= SEQUENCE {
    cfprEquipmentChassisFsmInstanceId                                CfprManagedObjectId,
    cfprEquipmentChassisFsmDn                                        CfprManagedObjectDn,
    cfprEquipmentChassisFsmRn                                        SnmpAdminString,
    cfprEquipmentChassisFsmCompletionTime                            DateAndTime,
    cfprEquipmentChassisFsmCurrentFsm                                CfprEquipmentChassisFsmCurrentFsm,
    cfprEquipmentChassisFsmDescrData                                 SnmpAdminString,
    cfprEquipmentChassisFsmFsmStatus                                 CfprFsmFsmStageStatus,
    cfprEquipmentChassisFsmProgress                                  Gauge32,
    cfprEquipmentChassisFsmRmtErrCode                                Gauge32,
    cfprEquipmentChassisFsmRmtErrDescr                               SnmpAdminString,
    cfprEquipmentChassisFsmRmtRslt                                   CfprConditionRemoteInvRslt
}

cfprEquipmentChassisFsmInstanceId OBJECT-TYPE
    SYNTAX       CfprManagedObjectId
    MAX-ACCESS   not-accessible
    STATUS       current
    DESCRIPTION
        "Instance identifier of the managed object."
    ::= { cfprEquipmentChassisFsmEntry 1 }

cfprEquipmentChassisFsmDn OBJECT-TYPE
    SYNTAX       CfprManagedObjectDn
    MAX-ACCESS   read-only
    STATUS       current
    DESCRIPTION
        "Cisco Firepower equipment:ChassisFsm:dn managed object property"
    ::= { cfprEquipmentChassisFsmEntry 2 }

cfprEquipmentChassisFsmRn OBJECT-TYPE
    SYNTAX       SnmpAdminString
    MAX-ACCESS   read-only
    STATUS       current
    DESCRIPTION
        "Cisco Firepower equipment:ChassisFsm:rn managed object property"
    ::= { cfprEquipmentChassisFsmEntry 3 }

cfprEquipmentChassisFsmCompletionTime OBJECT-TYPE
    SYNTAX       DateAndTime
    MAX-ACCESS   read-only
    STATUS       current
    DESCRIPTION
        "Cisco Firepower equipment:ChassisFsm:completionTime
        managed object property"
    ::= { cfprEquipmentChassisFsmEntry 4 }

cfprEquipmentChassisFsmCurrentFsm OBJECT-TYPE
    SYNTAX       CfprEquipmentChassisFsmCurrentFsm
    MAX-ACCESS   read-only
    STATUS       current
    DESCRIPTION
        "Cisco Firepower equipment:ChassisFsm:currentFsm
        managed object property"
    ::= { cfprEquipmentChassisFsmEntry 5 }

cfprEquipmentChassisFsmDescrData OBJECT-TYPE
    SYNTAX       SnmpAdminString
    MAX-ACCESS   read-only
    STATUS       current
    DESCRIPTION
        "Cisco Firepower equipment:ChassisFsm:descr managed
        object property"
    ::= { cfprEquipmentChassisFsmEntry 6 }

cfprEquipmentChassisFsmFsmStatus OBJECT-TYPE
    SYNTAX       CfprFsmFsmStageStatus
    MAX-ACCESS   read-only
    STATUS       current
    DESCRIPTION
        "Cisco Firepower equipment:ChassisFsm:fsmStatus
        managed object property"
    ::= { cfprEquipmentChassisFsmEntry 7 }

cfprEquipmentChassisFsmProgress OBJECT-TYPE
    SYNTAX       Gauge32
    MAX-ACCESS   read-only
    STATUS       current
    DESCRIPTION
        "Cisco Firepower equipment:ChassisFsm:progress
        managed object property"
    ::= { cfprEquipmentChassisFsmEntry 8 }

cfprEquipmentChassisFsmRmtErrCode OBJECT-TYPE
    SYNTAX       Gauge32
    MAX-ACCESS   read-only
    STATUS       current
    DESCRIPTION
        "Cisco Firepower equipment:ChassisFsm:rmtErrCode
        managed object property"
    ::= { cfprEquipmentChassisFsmEntry 9 }

cfprEquipmentChassisFsmRmtErrDescr OBJECT-TYPE
    SYNTAX       SnmpAdminString
    MAX-ACCESS   read-only
    STATUS       current
    DESCRIPTION
        "Cisco Firepower equipment:ChassisFsm:rmtErrDescr
        managed object property"
    ::= { cfprEquipmentChassisFsmEntry 10 }

cfprEquipmentChassisFsmRmtRslt OBJECT-TYPE
    SYNTAX       CfprConditionRemoteInvRslt
    MAX-ACCESS   read-only
    STATUS       current
    DESCRIPTION
        "Cisco Firepower equipment:ChassisFsm:rmtRslt managed
        object property"
    ::= { cfprEquipmentChassisFsmEntry 11 }

cfprEquipmentChassisFsmStageTable OBJECT-TYPE
    SYNTAX           SEQUENCE OF CfprEquipmentChassisFsmStageEntry
    MAX-ACCESS       not-accessible
    STATUS           current
    DESCRIPTION
        "Cisco Firepower equipment:ChassisFsmStage managed object table"
    ::= { cfprEquipmentObjects 24 }

cfprEquipmentChassisFsmStageEntry OBJECT-TYPE
    SYNTAX           CfprEquipmentChassisFsmStageEntry
    MAX-ACCESS       not-accessible
    STATUS           current
    DESCRIPTION
        "Entry for the cfprEquipmentChassisFsmStageTable table."
    INDEX { cfprEquipmentChassisFsmStageInstanceId }
    ::= { cfprEquipmentChassisFsmStageTable 1 }

CfprEquipmentChassisFsmStageEntry ::= SEQUENCE {
    cfprEquipmentChassisFsmStageInstanceId                           CfprManagedObjectId,
    cfprEquipmentChassisFsmStageDn                                   CfprManagedObjectDn,
    cfprEquipmentChassisFsmStageRn                                   SnmpAdminString,
    cfprEquipmentChassisFsmStageDescrData                            SnmpAdminString,
    cfprEquipmentChassisFsmStageLastUpdateTime                       DateAndTime,
    cfprEquipmentChassisFsmStageName                                 CfprEquipmentChassisFsmStageName,
    cfprEquipmentChassisFsmStageOrder                                Gauge32,
    cfprEquipmentChassisFsmStageRetry                                Gauge32,
    cfprEquipmentChassisFsmStageStageStatus                          CfprFsmFsmStageStatus
}

cfprEquipmentChassisFsmStageInstanceId OBJECT-TYPE
    SYNTAX       CfprManagedObjectId
    MAX-ACCESS   not-accessible
    STATUS       current
    DESCRIPTION
        "Instance identifier of the managed object."
    ::= { cfprEquipmentChassisFsmStageEntry 1 }

cfprEquipmentChassisFsmStageDn OBJECT-TYPE
    SYNTAX       CfprManagedObjectDn
    MAX-ACCESS   read-only
    STATUS       current
    DESCRIPTION
        "Cisco Firepower equipment:ChassisFsmStage:dn managed
        object property"
    ::= { cfprEquipmentChassisFsmStageEntry 2 }

cfprEquipmentChassisFsmStageRn OBJECT-TYPE
    SYNTAX       SnmpAdminString
    MAX-ACCESS   read-only
    STATUS       current
    DESCRIPTION
        "Cisco Firepower equipment:ChassisFsmStage:rn managed
        object property"
    ::= { cfprEquipmentChassisFsmStageEntry 3 }

cfprEquipmentChassisFsmStageDescrData OBJECT-TYPE
    SYNTAX       SnmpAdminString
    MAX-ACCESS   read-only
    STATUS       current
    DESCRIPTION
        "Cisco Firepower equipment:ChassisFsmStage:descr
        managed object property"
    ::= { cfprEquipmentChassisFsmStageEntry 4 }

cfprEquipmentChassisFsmStageLastUpdateTime OBJECT-TYPE
    SYNTAX       DateAndTime
    MAX-ACCESS   read-only
    STATUS       current
    DESCRIPTION
        "Cisco Firepower equipment:ChassisFsmStage:lastUpdateTime
        managed object property"
    ::= { cfprEquipmentChassisFsmStageEntry 5 }

cfprEquipmentChassisFsmStageName OBJECT-TYPE
    SYNTAX       CfprEquipmentChassisFsmStageName
    MAX-ACCESS   read-only
    STATUS       current
    DESCRIPTION
        "Cisco Firepower equipment:ChassisFsmStage:name
        managed object property"
    ::= { cfprEquipmentChassisFsmStageEntry 6 }

cfprEquipmentChassisFsmStageOrder OBJECT-TYPE
    SYNTAX       Gauge32
    MAX-ACCESS   read-only
    STATUS       current
    DESCRIPTION
        "Cisco Firepower equipment:ChassisFsmStage:order
        managed object property"
    ::= { cfprEquipmentChassisFsmStageEntry 7 }

cfprEquipmentChassisFsmStageRetry OBJECT-TYPE
    SYNTAX       Gauge32
    MAX-ACCESS   read-only
    STATUS       current
    DESCRIPTION
        "Cisco Firepower equipment:ChassisFsmStage:retry
        managed object property"
    ::= { cfprEquipmentChassisFsmStageEntry 8 }

cfprEquipmentChassisFsmStageStageStatus OBJECT-TYPE
    SYNTAX       CfprFsmFsmStageStatus
    MAX-ACCESS   read-only
    STATUS       current
    DESCRIPTION
        "Cisco Firepower equipment:ChassisFsmStage:stageStatus
        managed object property"
    ::= { cfprEquipmentChassisFsmStageEntry 9 }

cfprEquipmentChassisFsmTaskTable OBJECT-TYPE
    SYNTAX           SEQUENCE OF CfprEquipmentChassisFsmTaskEntry
    MAX-ACCESS       not-accessible
    STATUS           current
    DESCRIPTION
        "Cisco Firepower equipment:ChassisFsmTask managed object table"
    ::= { cfprEquipmentObjects 25 }

cfprEquipmentChassisFsmTaskEntry OBJECT-TYPE
    SYNTAX           CfprEquipmentChassisFsmTaskEntry
    MAX-ACCESS       not-accessible
    STATUS           current
    DESCRIPTION
        "Entry for the cfprEquipmentChassisFsmTaskTable table."
    INDEX { cfprEquipmentChassisFsmTaskInstanceId }
    ::= { cfprEquipmentChassisFsmTaskTable 1 }

CfprEquipmentChassisFsmTaskEntry ::= SEQUENCE {
    cfprEquipmentChassisFsmTaskInstanceId                            CfprManagedObjectId,
    cfprEquipmentChassisFsmTaskDn                                    CfprManagedObjectDn,
    cfprEquipmentChassisFsmTaskRn                                    SnmpAdminString,
    cfprEquipmentChassisFsmTaskCompletion                            CfprFsmCompletion,
    cfprEquipmentChassisFsmTaskFlags                                 CfprEquipmentChassisFsmTaskFlags,
    cfprEquipmentChassisFsmTaskItem                                  CfprEquipmentChassisFsmTaskItem,
    cfprEquipmentChassisFsmTaskSeqId                                 Gauge32
}

cfprEquipmentChassisFsmTaskInstanceId OBJECT-TYPE
    SYNTAX       CfprManagedObjectId
    MAX-ACCESS   not-accessible
    STATUS       current
    DESCRIPTION
        "Instance identifier of the managed object."
    ::= { cfprEquipmentChassisFsmTaskEntry 1 }

cfprEquipmentChassisFsmTaskDn OBJECT-TYPE
    SYNTAX       CfprManagedObjectDn
    MAX-ACCESS   read-only
    STATUS       current
    DESCRIPTION
        "Cisco Firepower equipment:ChassisFsmTask:dn managed
        object property"
    ::= { cfprEquipmentChassisFsmTaskEntry 2 }

cfprEquipmentChassisFsmTaskRn OBJECT-TYPE
    SYNTAX       SnmpAdminString
    MAX-ACCESS   read-only
    STATUS       current
    DESCRIPTION
        "Cisco Firepower equipment:ChassisFsmTask:rn managed
        object property"
    ::= { cfprEquipmentChassisFsmTaskEntry 3 }

cfprEquipmentChassisFsmTaskCompletion OBJECT-TYPE
    SYNTAX       CfprFsmCompletion
    MAX-ACCESS   read-only
    STATUS       current
    DESCRIPTION
        "Cisco Firepower equipment:ChassisFsmTask:completion
        managed object property"
    ::= { cfprEquipmentChassisFsmTaskEntry 4 }

cfprEquipmentChassisFsmTaskFlags OBJECT-TYPE
    SYNTAX       CfprEquipmentChassisFsmTaskFlags
    MAX-ACCESS   read-only
    STATUS       current
    DESCRIPTION
        "Cisco Firepower equipment:ChassisFsmTask:flags
        managed object property"
    ::= { cfprEquipmentChassisFsmTaskEntry 5 }

cfprEquipmentChassisFsmTaskItem OBJECT-TYPE
    SYNTAX       CfprEquipmentChassisFsmTaskItem
    MAX-ACCESS   read-only
    STATUS       current
    DESCRIPTION
        "Cisco Firepower equipment:ChassisFsmTask:item
        managed object property"
    ::= { cfprEquipmentChassisFsmTaskEntry 6 }

cfprEquipmentChassisFsmTaskSeqId OBJECT-TYPE
    SYNTAX       Gauge32
    MAX-ACCESS   read-only
    STATUS       current
    DESCRIPTION
        "Cisco Firepower equipment:ChassisFsmTask:seqId
        managed object property"
    ::= { cfprEquipmentChassisFsmTaskEntry 7 }

cfprEquipmentChassisStatsTable OBJECT-TYPE
    SYNTAX           SEQUENCE OF CfprEquipmentChassisStatsEntry
    MAX-ACCESS       not-accessible
    STATUS           current
    DESCRIPTION
        "Cisco Firepower equipment:ChassisStats managed object table"
    ::= { cfprEquipmentObjects 26 }

cfprEquipmentChassisStatsEntry OBJECT-TYPE
    SYNTAX           CfprEquipmentChassisStatsEntry
    MAX-ACCESS       not-accessible
    STATUS           current
    DESCRIPTION
        "Entry for the cfprEquipmentChassisStatsTable table."
    INDEX { cfprEquipmentChassisStatsInstanceId }
    ::= { cfprEquipmentChassisStatsTable 1 }

CfprEquipmentChassisStatsEntry ::= SEQUENCE {
    cfprEquipmentChassisStatsInstanceId                              CfprManagedObjectId,
    cfprEquipmentChassisStatsDn                                      CfprManagedObjectDn,
    cfprEquipmentChassisStatsRn                                      SnmpAdminString,
    cfprEquipmentChassisStatsInputPower                              INTEGER,
    cfprEquipmentChassisStatsInputPowerAvg                           INTEGER,
    cfprEquipmentChassisStatsInputPowerMax                           INTEGER,
    cfprEquipmentChassisStatsInputPowerMin                           INTEGER,
    cfprEquipmentChassisStatsIntervals                               Gauge32,
    cfprEquipmentChassisStatsOutputPower                             INTEGER,
    cfprEquipmentChassisStatsOutputPowerAvg                          INTEGER,
    cfprEquipmentChassisStatsOutputPowerMax                          INTEGER,
    cfprEquipmentChassisStatsOutputPowerMin                          INTEGER,
    cfprEquipmentChassisStatsSuspect                                 TruthValue,
    cfprEquipmentChassisStatsThresholded                             CfprEquipmentChassisStatsThresholded,
    cfprEquipmentChassisStatsTimeCollected                           DateAndTime,
    cfprEquipmentChassisStatsUpdate                                  Gauge32
}

cfprEquipmentChassisStatsInstanceId OBJECT-TYPE
    SYNTAX       CfprManagedObjectId
    MAX-ACCESS   not-accessible
    STATUS       current
    DESCRIPTION
        "Instance identifier of the managed object."
    ::= { cfprEquipmentChassisStatsEntry 1 }

cfprEquipmentChassisStatsDn OBJECT-TYPE
    SYNTAX       CfprManagedObjectDn
    MAX-ACCESS   read-only
    STATUS       current
    DESCRIPTION
        "Cisco Firepower equipment:ChassisStats:dn managed
        object property"
    ::= { cfprEquipmentChassisStatsEntry 2 }

cfprEquipmentChassisStatsRn OBJECT-TYPE
    SYNTAX       SnmpAdminString
    MAX-ACCESS   read-only
    STATUS       current
    DESCRIPTION
        "Cisco Firepower equipment:ChassisStats:rn managed
        object property"
    ::= { cfprEquipmentChassisStatsEntry 3 }

cfprEquipmentChassisStatsInputPower OBJECT-TYPE
    SYNTAX       INTEGER
    MAX-ACCESS   read-only
    STATUS       current
    DESCRIPTION
        "Cisco Firepower equipment:ChassisStats:inputPower
        managed object property"
    ::= { cfprEquipmentChassisStatsEntry 4 }

cfprEquipmentChassisStatsInputPowerAvg OBJECT-TYPE
    SYNTAX       INTEGER
    MAX-ACCESS   read-only
    STATUS       current
    DESCRIPTION
        "Cisco Firepower equipment:ChassisStats:inputPowerAvg
        managed object property"
    ::= { cfprEquipmentChassisStatsEntry 5 }

cfprEquipmentChassisStatsInputPowerMax OBJECT-TYPE
    SYNTAX       INTEGER
    MAX-ACCESS   read-only
    STATUS       current
    DESCRIPTION
        "Cisco Firepower equipment:ChassisStats:inputPowerMax
        managed object property"
    ::= { cfprEquipmentChassisStatsEntry 6 }

cfprEquipmentChassisStatsInputPowerMin OBJECT-TYPE
    SYNTAX       INTEGER
    MAX-ACCESS   read-only
    STATUS       current
    DESCRIPTION
        "Cisco Firepower equipment:ChassisStats:inputPowerMin
        managed object property"
    ::= { cfprEquipmentChassisStatsEntry 7 }

cfprEquipmentChassisStatsIntervals OBJECT-TYPE
    SYNTAX       Gauge32
    MAX-ACCESS   read-only
    STATUS       current
    DESCRIPTION
        "Cisco Firepower equipment:ChassisStats:intervals
        managed object property"
    ::= { cfprEquipmentChassisStatsEntry 8 }

cfprEquipmentChassisStatsOutputPower OBJECT-TYPE
    SYNTAX       INTEGER
    MAX-ACCESS   read-only
    STATUS       current
    DESCRIPTION
        "Cisco Firepower equipment:ChassisStats:outputPower
        managed object property"
    ::= { cfprEquipmentChassisStatsEntry 9 }

cfprEquipmentChassisStatsOutputPowerAvg OBJECT-TYPE
    SYNTAX       INTEGER
    MAX-ACCESS   read-only
    STATUS       current
    DESCRIPTION
        "Cisco Firepower equipment:ChassisStats:outputPowerAvg
        managed object property"
    ::= { cfprEquipmentChassisStatsEntry 10 }

cfprEquipmentChassisStatsOutputPowerMax OBJECT-TYPE
    SYNTAX       INTEGER
    MAX-ACCESS   read-only
    STATUS       current
    DESCRIPTION
        "Cisco Firepower equipment:ChassisStats:outputPowerMax
        managed object property"
    ::= { cfprEquipmentChassisStatsEntry 11 }

cfprEquipmentChassisStatsOutputPowerMin OBJECT-TYPE
    SYNTAX       INTEGER
    MAX-ACCESS   read-only
    STATUS       current
    DESCRIPTION
        "Cisco Firepower equipment:ChassisStats:outputPowerMin
        managed object property"
    ::= { cfprEquipmentChassisStatsEntry 12 }

cfprEquipmentChassisStatsSuspect OBJECT-TYPE
    SYNTAX       TruthValue
    MAX-ACCESS   read-only
    STATUS       current
    DESCRIPTION
        "Cisco Firepower equipment:ChassisStats:suspect
        managed object property"
    ::= { cfprEquipmentChassisStatsEntry 13 }

cfprEquipmentChassisStatsThresholded OBJECT-TYPE
    SYNTAX       CfprEquipmentChassisStatsThresholded
    MAX-ACCESS   read-only
    STATUS       current
    DESCRIPTION
        "Cisco Firepower equipment:ChassisStats:thresholded
        managed object property"
    ::= { cfprEquipmentChassisStatsEntry 14 }

cfprEquipmentChassisStatsTimeCollected OBJECT-TYPE
    SYNTAX       DateAndTime
    MAX-ACCESS   read-only
    STATUS       current
    DESCRIPTION
        "Cisco Firepower equipment:ChassisStats:timeCollected
        managed object property"
    ::= { cfprEquipmentChassisStatsEntry 15 }

cfprEquipmentChassisStatsUpdate OBJECT-TYPE
    SYNTAX       Gauge32
    MAX-ACCESS   read-only
    STATUS       current
    DESCRIPTION
        "Cisco Firepower equipment:ChassisStats:update
        managed object property"
    ::= { cfprEquipmentChassisStatsEntry 16 }

cfprEquipmentChassisStatsHistTable OBJECT-TYPE
    SYNTAX           SEQUENCE OF CfprEquipmentChassisStatsHistEntry
    MAX-ACCESS       not-accessible
    STATUS           current
    DESCRIPTION
        "Cisco Firepower equipment:ChassisStatsHist managed object table"
    ::= { cfprEquipmentObjects 27 }

cfprEquipmentChassisStatsHistEntry OBJECT-TYPE
    SYNTAX           CfprEquipmentChassisStatsHistEntry
    MAX-ACCESS       not-accessible
    STATUS           current
    DESCRIPTION
        "Entry for the cfprEquipmentChassisStatsHistTable table."
    INDEX { cfprEquipmentChassisStatsHistInstanceId }
    ::= { cfprEquipmentChassisStatsHistTable 1 }

CfprEquipmentChassisStatsHistEntry ::= SEQUENCE {
    cfprEquipmentChassisStatsHistInstanceId                          CfprManagedObjectId,
    cfprEquipmentChassisStatsHistDn                                  CfprManagedObjectDn,
    cfprEquipmentChassisStatsHistRn                                  SnmpAdminString,
    cfprEquipmentChassisStatsHistId                                  Unsigned64,
    cfprEquipmentChassisStatsHistInputPower                          INTEGER,
    cfprEquipmentChassisStatsHistInputPowerAvg                       INTEGER,
    cfprEquipmentChassisStatsHistInputPowerMax                       INTEGER,
    cfprEquipmentChassisStatsHistInputPowerMin                       INTEGER,
    cfprEquipmentChassisStatsHistMostRecent                          TruthValue,
    cfprEquipmentChassisStatsHistOutputPower                         INTEGER,
    cfprEquipmentChassisStatsHistOutputPowerAvg                      INTEGER,
    cfprEquipmentChassisStatsHistOutputPowerMax                      INTEGER,
    cfprEquipmentChassisStatsHistOutputPowerMin                      INTEGER,
    cfprEquipmentChassisStatsHistSuspect                             TruthValue,
    cfprEquipmentChassisStatsHistThresholded                         CfprEquipmentChassisStatsHistThresholded,
    cfprEquipmentChassisStatsHistTimeCollected                       DateAndTime
}

cfprEquipmentChassisStatsHistInstanceId OBJECT-TYPE
    SYNTAX       CfprManagedObjectId
    MAX-ACCESS   not-accessible
    STATUS       current
    DESCRIPTION
        "Instance identifier of the managed object."
    ::= { cfprEquipmentChassisStatsHistEntry 1 }

cfprEquipmentChassisStatsHistDn OBJECT-TYPE
    SYNTAX       CfprManagedObjectDn
    MAX-ACCESS   read-only
    STATUS       current
    DESCRIPTION
        "Cisco Firepower equipment:ChassisStatsHist:dn
        managed object property"
    ::= { cfprEquipmentChassisStatsHistEntry 2 }

cfprEquipmentChassisStatsHistRn OBJECT-TYPE
    SYNTAX       SnmpAdminString
    MAX-ACCESS   read-only
    STATUS       current
    DESCRIPTION
        "Cisco Firepower equipment:ChassisStatsHist:rn
        managed object property"
    ::= { cfprEquipmentChassisStatsHistEntry 3 }

cfprEquipmentChassisStatsHistId OBJECT-TYPE
    SYNTAX       Unsigned64
    MAX-ACCESS   read-only
    STATUS       current
    DESCRIPTION
        "Cisco Firepower equipment:ChassisStatsHist:id
        managed object property"
    ::= { cfprEquipmentChassisStatsHistEntry 4 }

cfprEquipmentChassisStatsHistInputPower OBJECT-TYPE
    SYNTAX       INTEGER
    MAX-ACCESS   read-only
    STATUS       current
    DESCRIPTION
        "Cisco Firepower equipment:ChassisStatsHist:inputPower
        managed object property"
    ::= { cfprEquipmentChassisStatsHistEntry 5 }

cfprEquipmentChassisStatsHistInputPowerAvg OBJECT-TYPE
    SYNTAX       INTEGER
    MAX-ACCESS   read-only
    STATUS       current
    DESCRIPTION
        "Cisco Firepower equipment:ChassisStatsHist:inputPowerAvg
        managed object property"
    ::= { cfprEquipmentChassisStatsHistEntry 6 }

cfprEquipmentChassisStatsHistInputPowerMax OBJECT-TYPE
    SYNTAX       INTEGER
    MAX-ACCESS   read-only
    STATUS       current
    DESCRIPTION
        "Cisco Firepower equipment:ChassisStatsHist:inputPowerMax
        managed object property"
    ::= { cfprEquipmentChassisStatsHistEntry 7 }

cfprEquipmentChassisStatsHistInputPowerMin OBJECT-TYPE
    SYNTAX       INTEGER
    MAX-ACCESS   read-only
    STATUS       current
    DESCRIPTION
        "Cisco Firepower equipment:ChassisStatsHist:inputPowerMin
        managed object property"
    ::= { cfprEquipmentChassisStatsHistEntry 8 }

cfprEquipmentChassisStatsHistMostRecent OBJECT-TYPE
    SYNTAX       TruthValue
    MAX-ACCESS   read-only
    STATUS       current
    DESCRIPTION
        "Cisco Firepower equipment:ChassisStatsHist:mostRecent
        managed object property"
    ::= { cfprEquipmentChassisStatsHistEntry 9 }

cfprEquipmentChassisStatsHistOutputPower OBJECT-TYPE
    SYNTAX       INTEGER
    MAX-ACCESS   read-only
    STATUS       current
    DESCRIPTION
        "Cisco Firepower equipment:ChassisStatsHist:outputPower
        managed object property"
    ::= { cfprEquipmentChassisStatsHistEntry 10 }

cfprEquipmentChassisStatsHistOutputPowerAvg OBJECT-TYPE
    SYNTAX       INTEGER
    MAX-ACCESS   read-only
    STATUS       current
    DESCRIPTION
        "Cisco Firepower equipment:ChassisStatsHist:outputPowerAvg
        managed object property"
    ::= { cfprEquipmentChassisStatsHistEntry 11 }

cfprEquipmentChassisStatsHistOutputPowerMax OBJECT-TYPE
    SYNTAX       INTEGER
    MAX-ACCESS   read-only
    STATUS       current
    DESCRIPTION
        "Cisco Firepower equipment:ChassisStatsHist:outputPowerMax
        managed object property"
    ::= { cfprEquipmentChassisStatsHistEntry 12 }

cfprEquipmentChassisStatsHistOutputPowerMin OBJECT-TYPE
    SYNTAX       INTEGER
    MAX-ACCESS   read-only
    STATUS       current
    DESCRIPTION
        "Cisco Firepower equipment:ChassisStatsHist:outputPowerMin
        managed object property"
    ::= { cfprEquipmentChassisStatsHistEntry 13 }

cfprEquipmentChassisStatsHistSuspect OBJECT-TYPE
    SYNTAX       TruthValue
    MAX-ACCESS   read-only
    STATUS       current
    DESCRIPTION
        "Cisco Firepower equipment:ChassisStatsHist:suspect
        managed object property"
    ::= { cfprEquipmentChassisStatsHistEntry 14 }

cfprEquipmentChassisStatsHistThresholded OBJECT-TYPE
    SYNTAX       CfprEquipmentChassisStatsHistThresholded
    MAX-ACCESS   read-only
    STATUS       current
    DESCRIPTION
        "Cisco Firepower equipment:ChassisStatsHist:thresholded
        managed object property"
    ::= { cfprEquipmentChassisStatsHistEntry 15 }

cfprEquipmentChassisStatsHistTimeCollected OBJECT-TYPE
    SYNTAX       DateAndTime
    MAX-ACCESS   read-only
    STATUS       current
    DESCRIPTION
        "Cisco Firepower equipment:ChassisStatsHist:timeCollected
        managed object property"
    ::= { cfprEquipmentChassisStatsHistEntry 16 }

cfprEquipmentCimcVmediaTable OBJECT-TYPE
    SYNTAX           SEQUENCE OF CfprEquipmentCimcVmediaEntry
    MAX-ACCESS       not-accessible
    STATUS           current
    DESCRIPTION
        "Cisco Firepower equipment:CimcVmedia managed object table"
    ::= { cfprEquipmentObjects 28 }

cfprEquipmentCimcVmediaEntry OBJECT-TYPE
    SYNTAX           CfprEquipmentCimcVmediaEntry
    MAX-ACCESS       not-accessible
    STATUS           current
    DESCRIPTION
        "Entry for the cfprEquipmentCimcVmediaTable table."
    INDEX { cfprEquipmentCimcVmediaInstanceId }
    ::= { cfprEquipmentCimcVmediaTable 1 }

CfprEquipmentCimcVmediaEntry ::= SEQUENCE {
    cfprEquipmentCimcVmediaInstanceId                                CfprManagedObjectId,
    cfprEquipmentCimcVmediaDn                                        CfprManagedObjectDn,
    cfprEquipmentCimcVmediaRn                                        SnmpAdminString,
    cfprEquipmentCimcVmediaDescr                                     SnmpAdminString,
    cfprEquipmentCimcVmediaIntId                                     SnmpAdminString,
    cfprEquipmentCimcVmediaIsSupported                               TruthValue,
    cfprEquipmentCimcVmediaMinBiosVersion                            SnmpAdminString,
    cfprEquipmentCimcVmediaMinCimcVersion                            SnmpAdminString,
    cfprEquipmentCimcVmediaName                                      SnmpAdminString,
    cfprEquipmentCimcVmediaPolicyLevel                               Gauge32,
    cfprEquipmentCimcVmediaPolicyOwner                               CfprPolicyPolicyOwner
}

cfprEquipmentCimcVmediaInstanceId OBJECT-TYPE
    SYNTAX       CfprManagedObjectId
    MAX-ACCESS   not-accessible
    STATUS       current
    DESCRIPTION
        "Instance identifier of the managed object."
    ::= { cfprEquipmentCimcVmediaEntry 1 }

cfprEquipmentCimcVmediaDn OBJECT-TYPE
    SYNTAX       CfprManagedObjectDn
    MAX-ACCESS   read-only
    STATUS       current
    DESCRIPTION
        "Cisco Firepower equipment:CimcVmedia:dn managed object property"
    ::= { cfprEquipmentCimcVmediaEntry 2 }

cfprEquipmentCimcVmediaRn OBJECT-TYPE
    SYNTAX       SnmpAdminString
    MAX-ACCESS   read-only
    STATUS       current
    DESCRIPTION
        "Cisco Firepower equipment:CimcVmedia:rn managed object property"
    ::= { cfprEquipmentCimcVmediaEntry 3 }

cfprEquipmentCimcVmediaDescr OBJECT-TYPE
    SYNTAX       SnmpAdminString
    MAX-ACCESS   read-only
    STATUS       current
    DESCRIPTION
        "Cisco Firepower equipment:CimcVmedia:descr managed
        object property"
    ::= { cfprEquipmentCimcVmediaEntry 4 }

cfprEquipmentCimcVmediaIntId OBJECT-TYPE
    SYNTAX       SnmpAdminString
    MAX-ACCESS   read-only
    STATUS       current
    DESCRIPTION
        "Cisco Firepower equipment:CimcVmedia:intId managed
        object property"
    ::= { cfprEquipmentCimcVmediaEntry 5 }

cfprEquipmentCimcVmediaIsSupported OBJECT-TYPE
    SYNTAX       TruthValue
    MAX-ACCESS   read-only
    STATUS       current
    DESCRIPTION
        "Cisco Firepower equipment:CimcVmedia:isSupported
        managed object property"
    ::= { cfprEquipmentCimcVmediaEntry 6 }

cfprEquipmentCimcVmediaMinBiosVersion OBJECT-TYPE
    SYNTAX       SnmpAdminString
    MAX-ACCESS   read-only
    STATUS       current
    DESCRIPTION
        "Cisco Firepower equipment:CimcVmedia:minBiosVersion
        managed object property"
    ::= { cfprEquipmentCimcVmediaEntry 7 }

cfprEquipmentCimcVmediaMinCimcVersion OBJECT-TYPE
    SYNTAX       SnmpAdminString
    MAX-ACCESS   read-only
    STATUS       current
    DESCRIPTION
        "Cisco Firepower equipment:CimcVmedia:minCimcVersion
        managed object property"
    ::= { cfprEquipmentCimcVmediaEntry 8 }

cfprEquipmentCimcVmediaName OBJECT-TYPE
    SYNTAX       SnmpAdminString
    MAX-ACCESS   read-only
    STATUS       current
    DESCRIPTION
        "Cisco Firepower equipment:CimcVmedia:name managed
        object property"
    ::= { cfprEquipmentCimcVmediaEntry 9 }

cfprEquipmentCimcVmediaPolicyLevel OBJECT-TYPE
    SYNTAX       Gauge32
    MAX-ACCESS   read-only
    STATUS       current
    DESCRIPTION
        "Cisco Firepower equipment:CimcVmedia:policyLevel
        managed object property"
    ::= { cfprEquipmentCimcVmediaEntry 10 }

cfprEquipmentCimcVmediaPolicyOwner OBJECT-TYPE
    SYNTAX       CfprPolicyPolicyOwner
    MAX-ACCESS   read-only
    STATUS       current
    DESCRIPTION
        "Cisco Firepower equipment:CimcVmedia:policyOwner
        managed object property"
    ::= { cfprEquipmentCimcVmediaEntry 11 }

cfprEquipmentDbgPluginCapProviderTable OBJECT-TYPE
    SYNTAX           SEQUENCE OF CfprEquipmentDbgPluginCapProviderEntry
    MAX-ACCESS       not-accessible
    STATUS           current
    DESCRIPTION
        "Cisco Firepower equipment:DbgPluginCapProvider
        managed object table"
    ::= { cfprEquipmentObjects 29 }

cfprEquipmentDbgPluginCapProviderEntry OBJECT-TYPE
    SYNTAX           CfprEquipmentDbgPluginCapProviderEntry
    MAX-ACCESS       not-accessible
    STATUS           current
    DESCRIPTION
        "Entry for the cfprEquipmentDbgPluginCapProviderTable table."
    INDEX { cfprEquipmentDbgPluginCapProviderInstanceId }
    ::= { cfprEquipmentDbgPluginCapProviderTable 1 }

CfprEquipmentDbgPluginCapProviderEntry ::= SEQUENCE {
    cfprEquipmentDbgPluginCapProviderInstanceId                      CfprManagedObjectId,
    cfprEquipmentDbgPluginCapProviderDn                              CfprManagedObjectDn,
    cfprEquipmentDbgPluginCapProviderRn                              SnmpAdminString,
    cfprEquipmentDbgPluginCapProviderDeleted                         TruthValue,
    cfprEquipmentDbgPluginCapProviderDeprecated                      TruthValue,
    cfprEquipmentDbgPluginCapProviderElementLoadFailures             Gauge32,
    cfprEquipmentDbgPluginCapProviderElementsLoaded                  Gauge32,
    cfprEquipmentDbgPluginCapProviderGencount                        Gauge32,
    cfprEquipmentDbgPluginCapProviderLoadErrors                      Gauge32,
    cfprEquipmentDbgPluginCapProviderLoadWarnings                    Gauge32,
    cfprEquipmentDbgPluginCapProviderMgmtPlaneVer                    SnmpAdminString,
    cfprEquipmentDbgPluginCapProviderModel                           SnmpAdminString,
    cfprEquipmentDbgPluginCapProviderPromCardType                    Gauge32,
    cfprEquipmentDbgPluginCapProviderRevision                        SnmpAdminString,
    cfprEquipmentDbgPluginCapProviderVendor                          SnmpAdminString
}

cfprEquipmentDbgPluginCapProviderInstanceId OBJECT-TYPE
    SYNTAX       CfprManagedObjectId
    MAX-ACCESS   not-accessible
    STATUS       current
    DESCRIPTION
        "Instance identifier of the managed object."
    ::= { cfprEquipmentDbgPluginCapProviderEntry 1 }

cfprEquipmentDbgPluginCapProviderDn OBJECT-TYPE
    SYNTAX       CfprManagedObjectDn
    MAX-ACCESS   read-only
    STATUS       current
    DESCRIPTION
        "Cisco Firepower equipment:DbgPluginCapProvider:dn
        managed object property"
    ::= { cfprEquipmentDbgPluginCapProviderEntry 2 }

cfprEquipmentDbgPluginCapProviderRn OBJECT-TYPE
    SYNTAX       SnmpAdminString
    MAX-ACCESS   read-only
    STATUS       current
    DESCRIPTION
        "Cisco Firepower equipment:DbgPluginCapProvider:rn
        managed object property"
    ::= { cfprEquipmentDbgPluginCapProviderEntry 3 }

cfprEquipmentDbgPluginCapProviderDeleted OBJECT-TYPE
    SYNTAX       TruthValue
    MAX-ACCESS   read-only
    STATUS       current
    DESCRIPTION
        "Cisco Firepower equipment:DbgPluginCapProvider:deleted
        managed object property"
    ::= { cfprEquipmentDbgPluginCapProviderEntry 4 }

cfprEquipmentDbgPluginCapProviderDeprecated OBJECT-TYPE
    SYNTAX       TruthValue
    MAX-ACCESS   read-only
    STATUS       current
    DESCRIPTION
        "Cisco Firepower equipment:DbgPluginCapProvider:deprecated
        managed object property"
    ::= { cfprEquipmentDbgPluginCapProviderEntry 5 }

cfprEquipmentDbgPluginCapProviderElementLoadFailures OBJECT-TYPE
    SYNTAX       Gauge32
    MAX-ACCESS   read-only
    STATUS       current
    DESCRIPTION
        "Cisco Firepower equipment:DbgPluginCapProvider:elementLoadFailure
        s managed object property"
    ::= { cfprEquipmentDbgPluginCapProviderEntry 6 }

cfprEquipmentDbgPluginCapProviderElementsLoaded OBJECT-TYPE
    SYNTAX       Gauge32
    MAX-ACCESS   read-only
    STATUS       current
    DESCRIPTION
        "Cisco Firepower equipment:DbgPluginCapProvider:elementsLoaded
        managed object property"
    ::= { cfprEquipmentDbgPluginCapProviderEntry 7 }

cfprEquipmentDbgPluginCapProviderGencount OBJECT-TYPE
    SYNTAX       Gauge32
    MAX-ACCESS   read-only
    STATUS       current
    DESCRIPTION
        "Cisco Firepower equipment:DbgPluginCapProvider:gencount
        managed object property"
    ::= { cfprEquipmentDbgPluginCapProviderEntry 8 }

cfprEquipmentDbgPluginCapProviderLoadErrors OBJECT-TYPE
    SYNTAX       Gauge32
    MAX-ACCESS   read-only
    STATUS       current
    DESCRIPTION
        "Cisco Firepower equipment:DbgPluginCapProvider:loadErrors
        managed object property"
    ::= { cfprEquipmentDbgPluginCapProviderEntry 9 }

cfprEquipmentDbgPluginCapProviderLoadWarnings OBJECT-TYPE
    SYNTAX       Gauge32
    MAX-ACCESS   read-only
    STATUS       current
    DESCRIPTION
        "Cisco Firepower equipment:DbgPluginCapProvider:loadWarnings
        managed object property"
    ::= { cfprEquipmentDbgPluginCapProviderEntry 10 }

cfprEquipmentDbgPluginCapProviderMgmtPlaneVer OBJECT-TYPE
    SYNTAX       SnmpAdminString
    MAX-ACCESS   read-only
    STATUS       current
    DESCRIPTION
        "Cisco Firepower equipment:DbgPluginCapProvider:mgmtPlaneVer
        managed object property"
    ::= { cfprEquipmentDbgPluginCapProviderEntry 11 }

cfprEquipmentDbgPluginCapProviderModel OBJECT-TYPE
    SYNTAX       SnmpAdminString
    MAX-ACCESS   read-only
    STATUS       current
    DESCRIPTION
        "Cisco Firepower equipment:DbgPluginCapProvider:model
        managed object property"
    ::= { cfprEquipmentDbgPluginCapProviderEntry 12 }

cfprEquipmentDbgPluginCapProviderPromCardType OBJECT-TYPE
    SYNTAX       Gauge32
    MAX-ACCESS   read-only
    STATUS       current
    DESCRIPTION
        "Cisco Firepower equipment:DbgPluginCapProvider:promCardType
        managed object property"
    ::= { cfprEquipmentDbgPluginCapProviderEntry 13 }

cfprEquipmentDbgPluginCapProviderRevision OBJECT-TYPE
    SYNTAX       SnmpAdminString
    MAX-ACCESS   read-only
    STATUS       current
    DESCRIPTION
        "Cisco Firepower equipment:DbgPluginCapProvider:revision
        managed object property"
    ::= { cfprEquipmentDbgPluginCapProviderEntry 14 }

cfprEquipmentDbgPluginCapProviderVendor OBJECT-TYPE
    SYNTAX       SnmpAdminString
    MAX-ACCESS   read-only
    STATUS       current
    DESCRIPTION
        "Cisco Firepower equipment:DbgPluginCapProvider:vendor
        managed object property"
    ::= { cfprEquipmentDbgPluginCapProviderEntry 15 }

cfprEquipmentDimmEntryTable OBJECT-TYPE
    SYNTAX           SEQUENCE OF CfprEquipmentDimmEntryEntry
    MAX-ACCESS       not-accessible
    STATUS           current
    DESCRIPTION
        "Cisco Firepower equipment:DimmEntry managed object table"
    ::= { cfprEquipmentObjects 30 }

cfprEquipmentDimmEntryEntry OBJECT-TYPE
    SYNTAX           CfprEquipmentDimmEntryEntry
    MAX-ACCESS       not-accessible
    STATUS           current
    DESCRIPTION
        "Entry for the cfprEquipmentDimmEntryTable table."
    INDEX { cfprEquipmentDimmEntryInstanceId }
    ::= { cfprEquipmentDimmEntryTable 1 }

CfprEquipmentDimmEntryEntry ::= SEQUENCE {
    cfprEquipmentDimmEntryInstanceId                                 CfprManagedObjectId,
    cfprEquipmentDimmEntryDn                                         CfprManagedObjectDn,
    cfprEquipmentDimmEntryRn                                         SnmpAdminString,
    cfprEquipmentDimmEntryId                                         Gauge32,
    cfprEquipmentDimmEntrySmbiosname                                 SnmpAdminString
}

cfprEquipmentDimmEntryInstanceId OBJECT-TYPE
    SYNTAX       CfprManagedObjectId
    MAX-ACCESS   not-accessible
    STATUS       current
    DESCRIPTION
        "Instance identifier of the managed object."
    ::= { cfprEquipmentDimmEntryEntry 1 }

cfprEquipmentDimmEntryDn OBJECT-TYPE
    SYNTAX       CfprManagedObjectDn
    MAX-ACCESS   read-only
    STATUS       current
    DESCRIPTION
        "Cisco Firepower equipment:DimmEntry:dn managed object property"
    ::= { cfprEquipmentDimmEntryEntry 2 }

cfprEquipmentDimmEntryRn OBJECT-TYPE
    SYNTAX       SnmpAdminString
    MAX-ACCESS   read-only
    STATUS       current
    DESCRIPTION
        "Cisco Firepower equipment:DimmEntry:rn managed object property"
    ::= { cfprEquipmentDimmEntryEntry 3 }

cfprEquipmentDimmEntryId OBJECT-TYPE
    SYNTAX       Gauge32
    MAX-ACCESS   read-only
    STATUS       current
    DESCRIPTION
        "Cisco Firepower equipment:DimmEntry:id managed object property"
    ::= { cfprEquipmentDimmEntryEntry 4 }

cfprEquipmentDimmEntrySmbiosname OBJECT-TYPE
    SYNTAX       SnmpAdminString
    MAX-ACCESS   read-only
    STATUS       current
    DESCRIPTION
        "Cisco Firepower equipment:DimmEntry:smbiosname
        managed object property"
    ::= { cfprEquipmentDimmEntryEntry 5 }

cfprEquipmentDimmMappingTable OBJECT-TYPE
    SYNTAX           SEQUENCE OF CfprEquipmentDimmMappingEntry
    MAX-ACCESS       not-accessible
    STATUS           current
    DESCRIPTION
        "Cisco Firepower equipment:DimmMapping managed object table"
    ::= { cfprEquipmentObjects 31 }

cfprEquipmentDimmMappingEntry OBJECT-TYPE
    SYNTAX           CfprEquipmentDimmMappingEntry
    MAX-ACCESS       not-accessible
    STATUS           current
    DESCRIPTION
        "Entry for the cfprEquipmentDimmMappingTable table."
    INDEX { cfprEquipmentDimmMappingInstanceId }
    ::= { cfprEquipmentDimmMappingTable 1 }

CfprEquipmentDimmMappingEntry ::= SEQUENCE {
    cfprEquipmentDimmMappingInstanceId                               CfprManagedObjectId,
    cfprEquipmentDimmMappingDn                                       CfprManagedObjectDn,
    cfprEquipmentDimmMappingRn                                       SnmpAdminString,
    cfprEquipmentDimmMappingDescr                                    SnmpAdminString,
    cfprEquipmentDimmMappingIntId                                    SnmpAdminString,
    cfprEquipmentDimmMappingName                                     SnmpAdminString,
    cfprEquipmentDimmMappingPolicyLevel                              Gauge32,
    cfprEquipmentDimmMappingPolicyOwner                              CfprPolicyPolicyOwner
}

cfprEquipmentDimmMappingInstanceId OBJECT-TYPE
    SYNTAX       CfprManagedObjectId
    MAX-ACCESS   not-accessible
    STATUS       current
    DESCRIPTION
        "Instance identifier of the managed object."
    ::= { cfprEquipmentDimmMappingEntry 1 }

cfprEquipmentDimmMappingDn OBJECT-TYPE
    SYNTAX       CfprManagedObjectDn
    MAX-ACCESS   read-only
    STATUS       current
    DESCRIPTION
        "Cisco Firepower equipment:DimmMapping:dn managed object property"
    ::= { cfprEquipmentDimmMappingEntry 2 }

cfprEquipmentDimmMappingRn OBJECT-TYPE
    SYNTAX       SnmpAdminString
    MAX-ACCESS   read-only
    STATUS       current
    DESCRIPTION
        "Cisco Firepower equipment:DimmMapping:rn managed object property"
    ::= { cfprEquipmentDimmMappingEntry 3 }

cfprEquipmentDimmMappingDescr OBJECT-TYPE
    SYNTAX       SnmpAdminString
    MAX-ACCESS   read-only
    STATUS       current
    DESCRIPTION
        "Cisco Firepower equipment:DimmMapping:descr managed
        object property"
    ::= { cfprEquipmentDimmMappingEntry 4 }

cfprEquipmentDimmMappingIntId OBJECT-TYPE
    SYNTAX       SnmpAdminString
    MAX-ACCESS   read-only
    STATUS       current
    DESCRIPTION
        "Cisco Firepower equipment:DimmMapping:intId managed
        object property"
    ::= { cfprEquipmentDimmMappingEntry 5 }

cfprEquipmentDimmMappingName OBJECT-TYPE
    SYNTAX       SnmpAdminString
    MAX-ACCESS   read-only
    STATUS       current
    DESCRIPTION
        "Cisco Firepower equipment:DimmMapping:name managed
        object property"
    ::= { cfprEquipmentDimmMappingEntry 6 }

cfprEquipmentDimmMappingPolicyLevel OBJECT-TYPE
    SYNTAX       Gauge32
    MAX-ACCESS   read-only
    STATUS       current
    DESCRIPTION
        "Cisco Firepower equipment:DimmMapping:policyLevel
        managed object property"
    ::= { cfprEquipmentDimmMappingEntry 7 }

cfprEquipmentDimmMappingPolicyOwner OBJECT-TYPE
    SYNTAX       CfprPolicyPolicyOwner
    MAX-ACCESS   read-only
    STATUS       current
    DESCRIPTION
        "Cisco Firepower equipment:DimmMapping:policyOwner
        managed object property"
    ::= { cfprEquipmentDimmMappingEntry 8 }

cfprEquipmentDiscoveryCapTable OBJECT-TYPE
    SYNTAX           SEQUENCE OF CfprEquipmentDiscoveryCapEntry
    MAX-ACCESS       not-accessible
    STATUS           current
    DESCRIPTION
        "Cisco Firepower equipment:DiscoveryCap managed object table"
    ::= { cfprEquipmentObjects 32 }

cfprEquipmentDiscoveryCapEntry OBJECT-TYPE
    SYNTAX           CfprEquipmentDiscoveryCapEntry
    MAX-ACCESS       not-accessible
    STATUS           current
    DESCRIPTION
        "Entry for the cfprEquipmentDiscoveryCapTable table."
    INDEX { cfprEquipmentDiscoveryCapInstanceId }
    ::= { cfprEquipmentDiscoveryCapTable 1 }

CfprEquipmentDiscoveryCapEntry ::= SEQUENCE {
    cfprEquipmentDiscoveryCapInstanceId                              CfprManagedObjectId,
    cfprEquipmentDiscoveryCapDn                                      CfprManagedObjectDn,
    cfprEquipmentDiscoveryCapRn                                      SnmpAdminString,
    cfprEquipmentDiscoveryCapOperPowerRequirement                    CfprEquipmentDiscoveryCapOperPowerRequirement
}

cfprEquipmentDiscoveryCapInstanceId OBJECT-TYPE
    SYNTAX       CfprManagedObjectId
    MAX-ACCESS   not-accessible
    STATUS       current
    DESCRIPTION
        "Instance identifier of the managed object."
    ::= { cfprEquipmentDiscoveryCapEntry 1 }

cfprEquipmentDiscoveryCapDn OBJECT-TYPE
    SYNTAX       CfprManagedObjectDn
    MAX-ACCESS   read-only
    STATUS       current
    DESCRIPTION
        "Cisco Firepower equipment:DiscoveryCap:dn managed
        object property"
    ::= { cfprEquipmentDiscoveryCapEntry 2 }

cfprEquipmentDiscoveryCapRn OBJECT-TYPE
    SYNTAX       SnmpAdminString
    MAX-ACCESS   read-only
    STATUS       current
    DESCRIPTION
        "Cisco Firepower equipment:DiscoveryCap:rn managed
        object property"
    ::= { cfprEquipmentDiscoveryCapEntry 3 }

cfprEquipmentDiscoveryCapOperPowerRequirement OBJECT-TYPE
    SYNTAX       CfprEquipmentDiscoveryCapOperPowerRequirement
    MAX-ACCESS   read-only
    STATUS       current
    DESCRIPTION
        "Cisco Firepower equipment:DiscoveryCap:operPowerRequirement
        managed object property"
    ::= { cfprEquipmentDiscoveryCapEntry 4 }

cfprEquipmentDowngradeConstraintTable OBJECT-TYPE
    SYNTAX           SEQUENCE OF CfprEquipmentDowngradeConstraintEntry
    MAX-ACCESS       not-accessible
    STATUS           current
    DESCRIPTION
        "Cisco Firepower equipment:DowngradeConstraint
        managed object table"
    ::= { cfprEquipmentObjects 33 }

cfprEquipmentDowngradeConstraintEntry OBJECT-TYPE
    SYNTAX           CfprEquipmentDowngradeConstraintEntry
    MAX-ACCESS       not-accessible
    STATUS           current
    DESCRIPTION
        "Entry for the cfprEquipmentDowngradeConstraintTable table."
    INDEX { cfprEquipmentDowngradeConstraintInstanceId }
    ::= { cfprEquipmentDowngradeConstraintTable 1 }

CfprEquipmentDowngradeConstraintEntry ::= SEQUENCE {
    cfprEquipmentDowngradeConstraintInstanceId                       CfprManagedObjectId,
    cfprEquipmentDowngradeConstraintDn                               CfprManagedObjectDn,
    cfprEquipmentDowngradeConstraintRn                               SnmpAdminString,
    cfprEquipmentDowngradeConstraintMinVer                           SnmpAdminString
}

cfprEquipmentDowngradeConstraintInstanceId OBJECT-TYPE
    SYNTAX       CfprManagedObjectId
    MAX-ACCESS   not-accessible
    STATUS       current
    DESCRIPTION
        "Instance identifier of the managed object."
    ::= { cfprEquipmentDowngradeConstraintEntry 1 }

cfprEquipmentDowngradeConstraintDn OBJECT-TYPE
    SYNTAX       CfprManagedObjectDn
    MAX-ACCESS   read-only
    STATUS       current
    DESCRIPTION
        "Cisco Firepower equipment:DowngradeConstraint:dn
        managed object property"
    ::= { cfprEquipmentDowngradeConstraintEntry 2 }

cfprEquipmentDowngradeConstraintRn OBJECT-TYPE
    SYNTAX       SnmpAdminString
    MAX-ACCESS   read-only
    STATUS       current
    DESCRIPTION
        "Cisco Firepower equipment:DowngradeConstraint:rn
        managed object property"
    ::= { cfprEquipmentDowngradeConstraintEntry 3 }

cfprEquipmentDowngradeConstraintMinVer OBJECT-TYPE
    SYNTAX       SnmpAdminString
    MAX-ACCESS   read-only
    STATUS       current
    DESCRIPTION
        "Cisco Firepower equipment:DowngradeConstraint:minVer
        managed object property"
    ::= { cfprEquipmentDowngradeConstraintEntry 4 }

cfprEquipmentEpmFpgaTable OBJECT-TYPE
    SYNTAX           SEQUENCE OF CfprEquipmentEpmFpgaEntry
    MAX-ACCESS       not-accessible
    STATUS           current
    DESCRIPTION
        "Cisco Firepower equipment:EpmFpga managed object table"
    ::= { cfprEquipmentObjects 150 }

cfprEquipmentEpmFpgaEntry OBJECT-TYPE
    SYNTAX           CfprEquipmentEpmFpgaEntry
    MAX-ACCESS       not-accessible
    STATUS           current
    DESCRIPTION
        "Entry for the cfprEquipmentEpmFpgaTable table."
    INDEX { cfprEquipmentEpmFpgaInstanceId }
    ::= { cfprEquipmentEpmFpgaTable 1 }

CfprEquipmentEpmFpgaEntry ::= SEQUENCE {
    cfprEquipmentEpmFpgaInstanceId                                   CfprManagedObjectId,
    cfprEquipmentEpmFpgaDn                                           CfprManagedObjectDn,
    cfprEquipmentEpmFpgaRn                                           SnmpAdminString,
    cfprEquipmentEpmFpgaImageName                                    SnmpAdminString,
    cfprEquipmentEpmFpgaBkupPackageVersion                           SnmpAdminString,
    cfprEquipmentEpmFpgaBkupVersion                                  SnmpAdminString,
    cfprEquipmentEpmFpgaFltAggr                                      Unsigned64,
    cfprEquipmentEpmFpgaIsOnline                                     TruthValue,
    cfprEquipmentEpmFpgaIsUpgradable                                 TruthValue,
    cfprEquipmentEpmFpgaModel                                        SnmpAdminString,
    cfprEquipmentEpmFpgaRevision                                     SnmpAdminString,
    cfprEquipmentEpmFpgaSerial                                       SnmpAdminString,
    cfprEquipmentEpmFpgaSlot                                         Gauge32,
    cfprEquipmentEpmFpgaTs                                           DateAndTime,
    cfprEquipmentEpmFpgaUpgradeStatus                                SnmpAdminString,
    cfprEquipmentEpmFpgaVendor                                       SnmpAdminString
}

cfprEquipmentEpmFpgaInstanceId OBJECT-TYPE
    SYNTAX       CfprManagedObjectId
    MAX-ACCESS   not-accessible
    STATUS       current
    DESCRIPTION
        "Instance identifier of the managed object."
    ::= { cfprEquipmentEpmFpgaEntry 1 }

cfprEquipmentEpmFpgaDn OBJECT-TYPE
    SYNTAX       CfprManagedObjectDn
    MAX-ACCESS   read-only
    STATUS       current
    DESCRIPTION
        "Cisco Firepower equipment:EpmFpga:dn managed object property"
    ::= { cfprEquipmentEpmFpgaEntry 2 }

cfprEquipmentEpmFpgaRn OBJECT-TYPE
    SYNTAX       SnmpAdminString
    MAX-ACCESS   read-only
    STATUS       current
    DESCRIPTION
        "Cisco Firepower equipment:EpmFpga:rn managed object property"
    ::= { cfprEquipmentEpmFpgaEntry 3 }

cfprEquipmentEpmFpgaImageName OBJECT-TYPE
    SYNTAX       SnmpAdminString
    MAX-ACCESS   read-only
    STATUS       current
    DESCRIPTION
        "Cisco Firepower equipment:EpmFpga:ImageName managed
        object property"
    ::= { cfprEquipmentEpmFpgaEntry 4 }

cfprEquipmentEpmFpgaBkupPackageVersion OBJECT-TYPE
    SYNTAX       SnmpAdminString
    MAX-ACCESS   read-only
    STATUS       current
    DESCRIPTION
        "Cisco Firepower equipment:EpmFpga:bkupPackageVersion
        managed object property"
    ::= { cfprEquipmentEpmFpgaEntry 5 }

cfprEquipmentEpmFpgaBkupVersion OBJECT-TYPE
    SYNTAX       SnmpAdminString
    MAX-ACCESS   read-only
    STATUS       current
    DESCRIPTION
        "Cisco Firepower equipment:EpmFpga:bkupVersion
        managed object property"
    ::= { cfprEquipmentEpmFpgaEntry 6 }

cfprEquipmentEpmFpgaFltAggr OBJECT-TYPE
    SYNTAX       Unsigned64
    MAX-ACCESS   read-only
    STATUS       current
    DESCRIPTION
        "Cisco Firepower equipment:EpmFpga:fltAggr managed
        object property"
    ::= { cfprEquipmentEpmFpgaEntry 7 }

cfprEquipmentEpmFpgaIsOnline OBJECT-TYPE
    SYNTAX       TruthValue
    MAX-ACCESS   read-only
    STATUS       current
    DESCRIPTION
        "Cisco Firepower equipment:EpmFpga:isOnline managed
        object property"
    ::= { cfprEquipmentEpmFpgaEntry 8 }

cfprEquipmentEpmFpgaIsUpgradable OBJECT-TYPE
    SYNTAX       TruthValue
    MAX-ACCESS   read-only
    STATUS       current
    DESCRIPTION
        "Cisco Firepower equipment:EpmFpga:isUpgradable
        managed object property"
    ::= { cfprEquipmentEpmFpgaEntry 9 }

cfprEquipmentEpmFpgaModel OBJECT-TYPE
    SYNTAX       SnmpAdminString
    MAX-ACCESS   read-only
    STATUS       current
    DESCRIPTION
        "Cisco Firepower equipment:EpmFpga:model managed object property"
    ::= { cfprEquipmentEpmFpgaEntry 10 }

cfprEquipmentEpmFpgaRevision OBJECT-TYPE
    SYNTAX       SnmpAdminString
    MAX-ACCESS   read-only
    STATUS       current
    DESCRIPTION
        "Cisco Firepower equipment:EpmFpga:revision managed
        object property"
    ::= { cfprEquipmentEpmFpgaEntry 11 }

cfprEquipmentEpmFpgaSerial OBJECT-TYPE
    SYNTAX       SnmpAdminString
    MAX-ACCESS   read-only
    STATUS       current
    DESCRIPTION
        "Cisco Firepower equipment:EpmFpga:serial managed object property"
    ::= { cfprEquipmentEpmFpgaEntry 12 }

cfprEquipmentEpmFpgaSlot OBJECT-TYPE
    SYNTAX       Gauge32
    MAX-ACCESS   read-only
    STATUS       current
    DESCRIPTION
        "Cisco Firepower equipment:EpmFpga:slot managed object property"
    ::= { cfprEquipmentEpmFpgaEntry 13 }

cfprEquipmentEpmFpgaTs OBJECT-TYPE
    SYNTAX       DateAndTime
    MAX-ACCESS   read-only
    STATUS       current
    DESCRIPTION
        "Cisco Firepower equipment:EpmFpga:ts managed object property"
    ::= { cfprEquipmentEpmFpgaEntry 14 }

cfprEquipmentEpmFpgaUpgradeStatus OBJECT-TYPE
    SYNTAX       SnmpAdminString
    MAX-ACCESS   read-only
    STATUS       current
    DESCRIPTION
        "Cisco Firepower equipment:EpmFpga:upgradeStatus
        managed object property"
    ::= { cfprEquipmentEpmFpgaEntry 15 }

cfprEquipmentEpmFpgaVendor OBJECT-TYPE
    SYNTAX       SnmpAdminString
    MAX-ACCESS   read-only
    STATUS       current
    DESCRIPTION
        "Cisco Firepower equipment:EpmFpga:vendor managed object property"
    ::= { cfprEquipmentEpmFpgaEntry 16 }

cfprEquipmentFailToWireCapProviderTable OBJECT-TYPE
    SYNTAX           SEQUENCE OF CfprEquipmentFailToWireCapProviderEntry
    MAX-ACCESS       not-accessible
    STATUS           current
    DESCRIPTION
        "Cisco Firepower equipment:FailToWireCapProvider
        managed object table"
    ::= { cfprEquipmentObjects 151 }

cfprEquipmentFailToWireCapProviderEntry OBJECT-TYPE
    SYNTAX           CfprEquipmentFailToWireCapProviderEntry
    MAX-ACCESS       not-accessible
    STATUS           current
    DESCRIPTION
        "Entry for the cfprEquipmentFailToWireCapProviderTable table."
    INDEX { cfprEquipmentFailToWireCapProviderInstanceId }
    ::= { cfprEquipmentFailToWireCapProviderTable 1 }

CfprEquipmentFailToWireCapProviderEntry ::= SEQUENCE {
    cfprEquipmentFailToWireCapProviderInstanceId                     CfprManagedObjectId,
    cfprEquipmentFailToWireCapProviderDn                             CfprManagedObjectDn,
    cfprEquipmentFailToWireCapProviderRn                             SnmpAdminString,
    cfprEquipmentFailToWireCapProviderDescr                          SnmpAdminString,
    cfprEquipmentFailToWireCapProviderIntId                          SnmpAdminString,
    cfprEquipmentFailToWireCapProviderName                           SnmpAdminString,
    cfprEquipmentFailToWireCapProviderPolicyLevel                    Gauge32,
    cfprEquipmentFailToWireCapProviderPolicyOwner                    CfprPolicyPolicyOwner
}

cfprEquipmentFailToWireCapProviderInstanceId OBJECT-TYPE
    SYNTAX       CfprManagedObjectId
    MAX-ACCESS   not-accessible
    STATUS       current
    DESCRIPTION
        "Instance identifier of the managed object."
    ::= { cfprEquipmentFailToWireCapProviderEntry 1 }

cfprEquipmentFailToWireCapProviderDn OBJECT-TYPE
    SYNTAX       CfprManagedObjectDn
    MAX-ACCESS   read-only
    STATUS       current
    DESCRIPTION
        "Cisco Firepower equipment:FailToWireCapProvider:dn
        managed object property"
    ::= { cfprEquipmentFailToWireCapProviderEntry 2 }

cfprEquipmentFailToWireCapProviderRn OBJECT-TYPE
    SYNTAX       SnmpAdminString
    MAX-ACCESS   read-only
    STATUS       current
    DESCRIPTION
        "Cisco Firepower equipment:FailToWireCapProvider:rn
        managed object property"
    ::= { cfprEquipmentFailToWireCapProviderEntry 3 }

cfprEquipmentFailToWireCapProviderDescr OBJECT-TYPE
    SYNTAX       SnmpAdminString
    MAX-ACCESS   read-only
    STATUS       current
    DESCRIPTION
        "Cisco Firepower equipment:FailToWireCapProvider:descr
        managed object property"
    ::= { cfprEquipmentFailToWireCapProviderEntry 4 }

cfprEquipmentFailToWireCapProviderIntId OBJECT-TYPE
    SYNTAX       SnmpAdminString
    MAX-ACCESS   read-only
    STATUS       current
    DESCRIPTION
        "Cisco Firepower equipment:FailToWireCapProvider:intId
        managed object property"
    ::= { cfprEquipmentFailToWireCapProviderEntry 5 }

cfprEquipmentFailToWireCapProviderName OBJECT-TYPE
    SYNTAX       SnmpAdminString
    MAX-ACCESS   read-only
    STATUS       current
    DESCRIPTION
        "Cisco Firepower equipment:FailToWireCapProvider:name
        managed object property"
    ::= { cfprEquipmentFailToWireCapProviderEntry 6 }

cfprEquipmentFailToWireCapProviderPolicyLevel OBJECT-TYPE
    SYNTAX       Gauge32
    MAX-ACCESS   read-only
    STATUS       current
    DESCRIPTION
        "Cisco Firepower equipment:FailToWireCapProvider:policyLevel
        managed object property"
    ::= { cfprEquipmentFailToWireCapProviderEntry 7 }

cfprEquipmentFailToWireCapProviderPolicyOwner OBJECT-TYPE
    SYNTAX       CfprPolicyPolicyOwner
    MAX-ACCESS   read-only
    STATUS       current
    DESCRIPTION
        "Cisco Firepower equipment:FailToWireCapProvider:policyOwner
        managed object property"
    ::= { cfprEquipmentFailToWireCapProviderEntry 8 }

cfprEquipmentFailToWirePortDefTable OBJECT-TYPE
    SYNTAX           SEQUENCE OF CfprEquipmentFailToWirePortDefEntry
    MAX-ACCESS       not-accessible
    STATUS           current
    DESCRIPTION
        "Cisco Firepower equipment:FailToWirePortDef managed object table"
    ::= { cfprEquipmentObjects 152 }

cfprEquipmentFailToWirePortDefEntry OBJECT-TYPE
    SYNTAX           CfprEquipmentFailToWirePortDefEntry
    MAX-ACCESS       not-accessible
    STATUS           current
    DESCRIPTION
        "Entry for the cfprEquipmentFailToWirePortDefTable table."
    INDEX { cfprEquipmentFailToWirePortDefInstanceId }
    ::= { cfprEquipmentFailToWirePortDefTable 1 }

CfprEquipmentFailToWirePortDefEntry ::= SEQUENCE {
    cfprEquipmentFailToWirePortDefInstanceId                         CfprManagedObjectId,
    cfprEquipmentFailToWirePortDefDn                                 CfprManagedObjectDn,
    cfprEquipmentFailToWirePortDefRn                                 SnmpAdminString,
    cfprEquipmentFailToWirePortDefAggrId                             Gauge32,
    cfprEquipmentFailToWirePortDefDescr                              SnmpAdminString,
    cfprEquipmentFailToWirePortDefIntId                              SnmpAdminString,
    cfprEquipmentFailToWirePortDefName                               SnmpAdminString,
    cfprEquipmentFailToWirePortDefPolicyLevel                        Gauge32,
    cfprEquipmentFailToWirePortDefPolicyOwner                        CfprPolicyPolicyOwner,
    cfprEquipmentFailToWirePortDefPortA                              Gauge32,
    cfprEquipmentFailToWirePortDefPortB                              Gauge32
}

cfprEquipmentFailToWirePortDefInstanceId OBJECT-TYPE
    SYNTAX       CfprManagedObjectId
    MAX-ACCESS   not-accessible
    STATUS       current
    DESCRIPTION
        "Instance identifier of the managed object."
    ::= { cfprEquipmentFailToWirePortDefEntry 1 }

cfprEquipmentFailToWirePortDefDn OBJECT-TYPE
    SYNTAX       CfprManagedObjectDn
    MAX-ACCESS   read-only
    STATUS       current
    DESCRIPTION
        "Cisco Firepower equipment:FailToWirePortDef:dn
        managed object property"
    ::= { cfprEquipmentFailToWirePortDefEntry 2 }

cfprEquipmentFailToWirePortDefRn OBJECT-TYPE
    SYNTAX       SnmpAdminString
    MAX-ACCESS   read-only
    STATUS       current
    DESCRIPTION
        "Cisco Firepower equipment:FailToWirePortDef:rn
        managed object property"
    ::= { cfprEquipmentFailToWirePortDefEntry 3 }

cfprEquipmentFailToWirePortDefAggrId OBJECT-TYPE
    SYNTAX       Gauge32
    MAX-ACCESS   read-only
    STATUS       current
    DESCRIPTION
        "Cisco Firepower equipment:FailToWirePortDef:aggrId
        managed object property"
    ::= { cfprEquipmentFailToWirePortDefEntry 4 }

cfprEquipmentFailToWirePortDefDescr OBJECT-TYPE
    SYNTAX       SnmpAdminString
    MAX-ACCESS   read-only
    STATUS       current
    DESCRIPTION
        "Cisco Firepower equipment:FailToWirePortDef:descr
        managed object property"
    ::= { cfprEquipmentFailToWirePortDefEntry 5 }

cfprEquipmentFailToWirePortDefIntId OBJECT-TYPE
    SYNTAX       SnmpAdminString
    MAX-ACCESS   read-only
    STATUS       current
    DESCRIPTION
        "Cisco Firepower equipment:FailToWirePortDef:intId
        managed object property"
    ::= { cfprEquipmentFailToWirePortDefEntry 6 }

cfprEquipmentFailToWirePortDefName OBJECT-TYPE
    SYNTAX       SnmpAdminString
    MAX-ACCESS   read-only
    STATUS       current
    DESCRIPTION
        "Cisco Firepower equipment:FailToWirePortDef:name
        managed object property"
    ::= { cfprEquipmentFailToWirePortDefEntry 7 }

cfprEquipmentFailToWirePortDefPolicyLevel OBJECT-TYPE
    SYNTAX       Gauge32
    MAX-ACCESS   read-only
    STATUS       current
    DESCRIPTION
        "Cisco Firepower equipment:FailToWirePortDef:policyLevel
        managed object property"
    ::= { cfprEquipmentFailToWirePortDefEntry 8 }

cfprEquipmentFailToWirePortDefPolicyOwner OBJECT-TYPE
    SYNTAX       CfprPolicyPolicyOwner
    MAX-ACCESS   read-only
    STATUS       current
    DESCRIPTION
        "Cisco Firepower equipment:FailToWirePortDef:policyOwner
        managed object property"
    ::= { cfprEquipmentFailToWirePortDefEntry 9 }

cfprEquipmentFailToWirePortDefPortA OBJECT-TYPE
    SYNTAX       Gauge32
    MAX-ACCESS   read-only
    STATUS       current
    DESCRIPTION
        "Cisco Firepower equipment:FailToWirePortDef:portA
        managed object property"
    ::= { cfprEquipmentFailToWirePortDefEntry 10 }

cfprEquipmentFailToWirePortDefPortB OBJECT-TYPE
    SYNTAX       Gauge32
    MAX-ACCESS   read-only
    STATUS       current
    DESCRIPTION
        "Cisco Firepower equipment:FailToWirePortDef:portB
        managed object property"
    ::= { cfprEquipmentFailToWirePortDefEntry 11 }

cfprEquipmentFanTable OBJECT-TYPE
    SYNTAX           SEQUENCE OF CfprEquipmentFanEntry
    MAX-ACCESS       not-accessible
    STATUS           current
    DESCRIPTION
        "Cisco Firepower equipment:Fan managed object table"
    ::= { cfprEquipmentObjects 34 }

cfprEquipmentFanEntry OBJECT-TYPE
    SYNTAX           CfprEquipmentFanEntry
    MAX-ACCESS       not-accessible
    STATUS           current
    DESCRIPTION
        "Entry for the cfprEquipmentFanTable table."
    INDEX { cfprEquipmentFanInstanceId }
    ::= { cfprEquipmentFanTable 1 }

CfprEquipmentFanEntry ::= SEQUENCE {
    cfprEquipmentFanInstanceId                                       CfprManagedObjectId,
    cfprEquipmentFanDn                                               CfprManagedObjectDn,
    cfprEquipmentFanRn                                               SnmpAdminString,
    cfprEquipmentFanFltAggr                                          Unsigned64,
    cfprEquipmentFanId                                               CfprEquipmentFanId,
    cfprEquipmentFanIntType                                          CfprEquipmentInternalFanType,
    cfprEquipmentFanModel                                            SnmpAdminString,
    cfprEquipmentFanModule                                           CfprEquipmentFanModule,
    cfprEquipmentFanOperQualifierReason                              SnmpAdminString,
    cfprEquipmentFanOperState                                        CfprEquipmentOperability,
    cfprEquipmentFanOperability                                      CfprEquipmentOperability,
    cfprEquipmentFanPerf                                             CfprEquipmentSensorThresholdStatus,
    cfprEquipmentFanPower                                            CfprEquipmentPowerState,
    cfprEquipmentFanPresence                                         CfprEquipmentPresence,
    cfprEquipmentFanRevision                                         SnmpAdminString,
    cfprEquipmentFanSerial                                           SnmpAdminString,
    cfprEquipmentFanThermal                                          CfprEquipmentSensorThresholdStatus,
    cfprEquipmentFanTray                                             CfprEquipmentFanTray,
    cfprEquipmentFanVendor                                           SnmpAdminString,
    cfprEquipmentFanVoltage                                          CfprEquipmentSensorThresholdStatus
}

cfprEquipmentFanInstanceId OBJECT-TYPE
    SYNTAX       CfprManagedObjectId
    MAX-ACCESS   not-accessible
    STATUS       current
    DESCRIPTION
        "Instance identifier of the managed object."
    ::= { cfprEquipmentFanEntry 1 }

cfprEquipmentFanDn OBJECT-TYPE
    SYNTAX       CfprManagedObjectDn
    MAX-ACCESS   read-only
    STATUS       current
    DESCRIPTION
        "Cisco Firepower equipment:Fan:dn managed object property"
    ::= { cfprEquipmentFanEntry 2 }

cfprEquipmentFanRn OBJECT-TYPE
    SYNTAX       SnmpAdminString
    MAX-ACCESS   read-only
    STATUS       current
    DESCRIPTION
        "Cisco Firepower equipment:Fan:rn managed object property"
    ::= { cfprEquipmentFanEntry 3 }

cfprEquipmentFanFltAggr OBJECT-TYPE
    SYNTAX       Unsigned64
    MAX-ACCESS   read-only
    STATUS       current
    DESCRIPTION
        "Cisco Firepower equipment:Fan:fltAggr managed object property"
    ::= { cfprEquipmentFanEntry 4 }

cfprEquipmentFanId OBJECT-TYPE
    SYNTAX       CfprEquipmentFanId
    MAX-ACCESS   read-only
    STATUS       current
    DESCRIPTION
        "Cisco Firepower equipment:Fan:id managed object property"
    ::= { cfprEquipmentFanEntry 5 }

cfprEquipmentFanIntType OBJECT-TYPE
    SYNTAX       CfprEquipmentInternalFanType
    MAX-ACCESS   read-only
    STATUS       current
    DESCRIPTION
        "Cisco Firepower equipment:Fan:intType managed object property"
    ::= { cfprEquipmentFanEntry 6 }

cfprEquipmentFanModel OBJECT-TYPE
    SYNTAX       SnmpAdminString
    MAX-ACCESS   read-only
    STATUS       current
    DESCRIPTION
        "Cisco Firepower equipment:Fan:model managed object property"
    ::= { cfprEquipmentFanEntry 7 }

cfprEquipmentFanModule OBJECT-TYPE
    SYNTAX       CfprEquipmentFanModule
    MAX-ACCESS   read-only
    STATUS       current
    DESCRIPTION
        "Cisco Firepower equipment:Fan:module managed object property"
    ::= { cfprEquipmentFanEntry 8 }

cfprEquipmentFanOperQualifierReason OBJECT-TYPE
    SYNTAX       SnmpAdminString
    MAX-ACCESS   read-only
    STATUS       current
    DESCRIPTION
        "Cisco Firepower equipment:Fan:operQualifierReason
        managed object property"
    ::= { cfprEquipmentFanEntry 9 }

cfprEquipmentFanOperState OBJECT-TYPE
    SYNTAX       CfprEquipmentOperability
    MAX-ACCESS   read-only
    STATUS       current
    DESCRIPTION
        "Cisco Firepower equipment:Fan:operState managed object property"
    ::= { cfprEquipmentFanEntry 10 }

cfprEquipmentFanOperability OBJECT-TYPE
    SYNTAX       CfprEquipmentOperability
    MAX-ACCESS   read-only
    STATUS       current
    DESCRIPTION
        "Cisco Firepower equipment:Fan:operability managed
        object property"
    ::= { cfprEquipmentFanEntry 11 }

cfprEquipmentFanPerf OBJECT-TYPE
    SYNTAX       CfprEquipmentSensorThresholdStatus
    MAX-ACCESS   read-only
    STATUS       current
    DESCRIPTION
        "Cisco Firepower equipment:Fan:perf managed object property"
    ::= { cfprEquipmentFanEntry 12 }

cfprEquipmentFanPower OBJECT-TYPE
    SYNTAX       CfprEquipmentPowerState
    MAX-ACCESS   read-only
    STATUS       current
    DESCRIPTION
        "Cisco Firepower equipment:Fan:power managed object property"
    ::= { cfprEquipmentFanEntry 13 }

cfprEquipmentFanPresence OBJECT-TYPE
    SYNTAX       CfprEquipmentPresence
    MAX-ACCESS   read-only
    STATUS       current
    DESCRIPTION
        "Cisco Firepower equipment:Fan:presence managed object property"
    ::= { cfprEquipmentFanEntry 14 }

cfprEquipmentFanRevision OBJECT-TYPE
    SYNTAX       SnmpAdminString
    MAX-ACCESS   read-only
    STATUS       current
    DESCRIPTION
        "Cisco Firepower equipment:Fan:revision managed object property"
    ::= { cfprEquipmentFanEntry 15 }

cfprEquipmentFanSerial OBJECT-TYPE
    SYNTAX       SnmpAdminString
    MAX-ACCESS   read-only
    STATUS       current
    DESCRIPTION
        "Cisco Firepower equipment:Fan:serial managed object property"
    ::= { cfprEquipmentFanEntry 16 }

cfprEquipmentFanThermal OBJECT-TYPE
    SYNTAX       CfprEquipmentSensorThresholdStatus
    MAX-ACCESS   read-only
    STATUS       current
    DESCRIPTION
        "Cisco Firepower equipment:Fan:thermal managed object property"
    ::= { cfprEquipmentFanEntry 17 }

cfprEquipmentFanTray OBJECT-TYPE
    SYNTAX       CfprEquipmentFanTray
    MAX-ACCESS   read-only
    STATUS       current
    DESCRIPTION
        "Cisco Firepower equipment:Fan:tray managed object property"
    ::= { cfprEquipmentFanEntry 18 }

cfprEquipmentFanVendor OBJECT-TYPE
    SYNTAX       SnmpAdminString
    MAX-ACCESS   read-only
    STATUS       current
    DESCRIPTION
        "Cisco Firepower equipment:Fan:vendor managed object property"
    ::= { cfprEquipmentFanEntry 19 }

cfprEquipmentFanVoltage OBJECT-TYPE
    SYNTAX       CfprEquipmentSensorThresholdStatus
    MAX-ACCESS   read-only
    STATUS       current
    DESCRIPTION
        "Cisco Firepower equipment:Fan:voltage managed object property"
    ::= { cfprEquipmentFanEntry 20 }

cfprEquipmentFanEnvTable OBJECT-TYPE
    SYNTAX           SEQUENCE OF CfprEquipmentFanEnvEntry
    MAX-ACCESS       not-accessible
    STATUS           current
    DESCRIPTION
        "Cisco Firepower equipment:FanEnv managed object table"
    ::= { cfprEquipmentObjects 153 }

cfprEquipmentFanEnvEntry OBJECT-TYPE
    SYNTAX           CfprEquipmentFanEnvEntry
    MAX-ACCESS       not-accessible
    STATUS           current
    DESCRIPTION
        "Entry for the cfprEquipmentFanEnvTable table."
    INDEX { cfprEquipmentFanEnvInstanceId }
    ::= { cfprEquipmentFanEnvTable 1 }

CfprEquipmentFanEnvEntry ::= SEQUENCE {
    cfprEquipmentFanEnvInstanceId                                    CfprManagedObjectId,
    cfprEquipmentFanEnvDn                                            CfprManagedObjectDn,
    cfprEquipmentFanEnvRn                                            SnmpAdminString,
    cfprEquipmentFanEnvFanFrontspeed                                 Gauge32,
    cfprEquipmentFanEnvFanPerf                                       CfprEquipmentSensorThresholdStatus,
    cfprEquipmentFanEnvFanRearspeed                                  Gauge32,
    cfprEquipmentFanEnvFanSpeed                                      Gauge32,
    cfprEquipmentFanEnvFanStatus                                     CfprEquipmentOperability,
    cfprEquipmentFanEnvId                                            Gauge32
}

cfprEquipmentFanEnvInstanceId OBJECT-TYPE
    SYNTAX       CfprManagedObjectId
    MAX-ACCESS   not-accessible
    STATUS       current
    DESCRIPTION
        "Instance identifier of the managed object."
    ::= { cfprEquipmentFanEnvEntry 1 }

cfprEquipmentFanEnvDn OBJECT-TYPE
    SYNTAX       CfprManagedObjectDn
    MAX-ACCESS   read-only
    STATUS       current
    DESCRIPTION
        "Cisco Firepower equipment:FanEnv:dn managed object property"
    ::= { cfprEquipmentFanEnvEntry 2 }

cfprEquipmentFanEnvRn OBJECT-TYPE
    SYNTAX       SnmpAdminString
    MAX-ACCESS   read-only
    STATUS       current
    DESCRIPTION
        "Cisco Firepower equipment:FanEnv:rn managed object property"
    ::= { cfprEquipmentFanEnvEntry 3 }

cfprEquipmentFanEnvFanFrontspeed OBJECT-TYPE
    SYNTAX       Gauge32
    MAX-ACCESS   read-only
    STATUS       current
    DESCRIPTION
        "Cisco Firepower equipment:FanEnv:fanFrontspeed
        managed object property"
    ::= { cfprEquipmentFanEnvEntry 4 }

cfprEquipmentFanEnvFanPerf OBJECT-TYPE
    SYNTAX       CfprEquipmentSensorThresholdStatus
    MAX-ACCESS   read-only
    STATUS       current
    DESCRIPTION
        "Cisco Firepower equipment:FanEnv:fanPerf managed object property"
    ::= { cfprEquipmentFanEnvEntry 5 }

cfprEquipmentFanEnvFanRearspeed OBJECT-TYPE
    SYNTAX       Gauge32
    MAX-ACCESS   read-only
    STATUS       current
    DESCRIPTION
        "Cisco Firepower equipment:FanEnv:fanRearspeed
        managed object property"
    ::= { cfprEquipmentFanEnvEntry 6 }

cfprEquipmentFanEnvFanSpeed OBJECT-TYPE
    SYNTAX       Gauge32
    MAX-ACCESS   read-only
    STATUS       current
    DESCRIPTION
        "Cisco Firepower equipment:FanEnv:fanSpeed managed
        object property"
    ::= { cfprEquipmentFanEnvEntry 7 }

cfprEquipmentFanEnvFanStatus OBJECT-TYPE
    SYNTAX       CfprEquipmentOperability
    MAX-ACCESS   read-only
    STATUS       current
    DESCRIPTION
        "Cisco Firepower equipment:FanEnv:fanStatus managed
        object property"
    ::= { cfprEquipmentFanEnvEntry 8 }

cfprEquipmentFanEnvId OBJECT-TYPE
    SYNTAX       Gauge32
    MAX-ACCESS   read-only
    STATUS       current
    DESCRIPTION
        "Cisco Firepower equipment:FanEnv:id managed object property"
    ::= { cfprEquipmentFanEnvEntry 9 }

cfprEquipmentFanModuleTable OBJECT-TYPE
    SYNTAX           SEQUENCE OF CfprEquipmentFanModuleEntry
    MAX-ACCESS       not-accessible
    STATUS           current
    DESCRIPTION
        "Cisco Firepower equipment:FanModule managed object table"
    ::= { cfprEquipmentObjects 35 }

cfprEquipmentFanModuleEntry OBJECT-TYPE
    SYNTAX           CfprEquipmentFanModuleEntry
    MAX-ACCESS       not-accessible
    STATUS           current
    DESCRIPTION
        "Entry for the cfprEquipmentFanModuleTable table."
    INDEX { cfprEquipmentFanModuleInstanceId }
    ::= { cfprEquipmentFanModuleTable 1 }

CfprEquipmentFanModuleEntry ::= SEQUENCE {
    cfprEquipmentFanModuleInstanceId                                 CfprManagedObjectId,
    cfprEquipmentFanModuleDn                                         CfprManagedObjectDn,
    cfprEquipmentFanModuleRn                                         SnmpAdminString,
    cfprEquipmentFanModuleFltAggr                                    Unsigned64,
    cfprEquipmentFanModuleId                                         CfprEquipmentFanModuleId,
    cfprEquipmentFanModuleMfgTime                                    DateAndTime,
    cfprEquipmentFanModuleModel                                      SnmpAdminString,
    cfprEquipmentFanModuleOperQualifierReason                        SnmpAdminString,
    cfprEquipmentFanModuleOperState                                  CfprEquipmentOperability,
    cfprEquipmentFanModuleOperability                                CfprEquipmentOperability,
    cfprEquipmentFanModulePartNumber                                 SnmpAdminString,
    cfprEquipmentFanModulePerf                                       CfprEquipmentSensorThresholdStatus,
    cfprEquipmentFanModulePower                                      CfprEquipmentPowerState,
    cfprEquipmentFanModulePresence                                   CfprEquipmentPresence,
    cfprEquipmentFanModuleRevision                                   SnmpAdminString,
    cfprEquipmentFanModuleSerial                                     SnmpAdminString,
    cfprEquipmentFanModuleThermal                                    CfprEquipmentSensorThresholdStatus,
    cfprEquipmentFanModuleTray                                       CfprEquipmentFanModuleTray,
    cfprEquipmentFanModuleVendor                                     SnmpAdminString,
    cfprEquipmentFanModuleVid                                        SnmpAdminString,
    cfprEquipmentFanModuleVoltage                                    CfprEquipmentSensorThresholdStatus
}

cfprEquipmentFanModuleInstanceId OBJECT-TYPE
    SYNTAX       CfprManagedObjectId
    MAX-ACCESS   not-accessible
    STATUS       current
    DESCRIPTION
        "Instance identifier of the managed object."
    ::= { cfprEquipmentFanModuleEntry 1 }

cfprEquipmentFanModuleDn OBJECT-TYPE
    SYNTAX       CfprManagedObjectDn
    MAX-ACCESS   read-only
    STATUS       current
    DESCRIPTION
        "Cisco Firepower equipment:FanModule:dn managed object property"
    ::= { cfprEquipmentFanModuleEntry 2 }

cfprEquipmentFanModuleRn OBJECT-TYPE
    SYNTAX       SnmpAdminString
    MAX-ACCESS   read-only
    STATUS       current
    DESCRIPTION
        "Cisco Firepower equipment:FanModule:rn managed object property"
    ::= { cfprEquipmentFanModuleEntry 3 }

cfprEquipmentFanModuleFltAggr OBJECT-TYPE
    SYNTAX       Unsigned64
    MAX-ACCESS   read-only
    STATUS       current
    DESCRIPTION
        "Cisco Firepower equipment:FanModule:fltAggr managed
        object property"
    ::= { cfprEquipmentFanModuleEntry 4 }

cfprEquipmentFanModuleId OBJECT-TYPE
    SYNTAX       CfprEquipmentFanModuleId
    MAX-ACCESS   read-only
    STATUS       current
    DESCRIPTION
        "Cisco Firepower equipment:FanModule:id managed object property"
    ::= { cfprEquipmentFanModuleEntry 5 }

cfprEquipmentFanModuleMfgTime OBJECT-TYPE
    SYNTAX       DateAndTime
    MAX-ACCESS   read-only
    STATUS       current
    DESCRIPTION
        "Cisco Firepower equipment:FanModule:mfgTime managed
        object property"
    ::= { cfprEquipmentFanModuleEntry 6 }

cfprEquipmentFanModuleModel OBJECT-TYPE
    SYNTAX       SnmpAdminString
    MAX-ACCESS   read-only
    STATUS       current
    DESCRIPTION
        "Cisco Firepower equipment:FanModule:model managed
        object property"
    ::= { cfprEquipmentFanModuleEntry 7 }

cfprEquipmentFanModuleOperQualifierReason OBJECT-TYPE
    SYNTAX       SnmpAdminString
    MAX-ACCESS   read-only
    STATUS       current
    DESCRIPTION
        "Cisco Firepower equipment:FanModule:operQualifierReason
        managed object property"
    ::= { cfprEquipmentFanModuleEntry 8 }

cfprEquipmentFanModuleOperState OBJECT-TYPE
    SYNTAX       CfprEquipmentOperability
    MAX-ACCESS   read-only
    STATUS       current
    DESCRIPTION
        "Cisco Firepower equipment:FanModule:operState
        managed object property"
    ::= { cfprEquipmentFanModuleEntry 9 }

cfprEquipmentFanModuleOperability OBJECT-TYPE
    SYNTAX       CfprEquipmentOperability
    MAX-ACCESS   read-only
    STATUS       current
    DESCRIPTION
        "Cisco Firepower equipment:FanModule:operability
        managed object property"
    ::= { cfprEquipmentFanModuleEntry 10 }

cfprEquipmentFanModulePartNumber OBJECT-TYPE
    SYNTAX       SnmpAdminString
    MAX-ACCESS   read-only
    STATUS       current
    DESCRIPTION
        "Cisco Firepower equipment:FanModule:partNumber
        managed object property"
    ::= { cfprEquipmentFanModuleEntry 11 }

cfprEquipmentFanModulePerf OBJECT-TYPE
    SYNTAX       CfprEquipmentSensorThresholdStatus
    MAX-ACCESS   read-only
    STATUS       current
    DESCRIPTION
        "Cisco Firepower equipment:FanModule:perf managed object property"
    ::= { cfprEquipmentFanModuleEntry 12 }

cfprEquipmentFanModulePower OBJECT-TYPE
    SYNTAX       CfprEquipmentPowerState
    MAX-ACCESS   read-only
    STATUS       current
    DESCRIPTION
        "Cisco Firepower equipment:FanModule:power managed
        object property"
    ::= { cfprEquipmentFanModuleEntry 13 }

cfprEquipmentFanModulePresence OBJECT-TYPE
    SYNTAX       CfprEquipmentPresence
    MAX-ACCESS   read-only
    STATUS       current
    DESCRIPTION
        "Cisco Firepower equipment:FanModule:presence managed
        object property"
    ::= { cfprEquipmentFanModuleEntry 14 }

cfprEquipmentFanModuleRevision OBJECT-TYPE
    SYNTAX       SnmpAdminString
    MAX-ACCESS   read-only
    STATUS       current
    DESCRIPTION
        "Cisco Firepower equipment:FanModule:revision managed
        object property"
    ::= { cfprEquipmentFanModuleEntry 15 }

cfprEquipmentFanModuleSerial OBJECT-TYPE
    SYNTAX       SnmpAdminString
    MAX-ACCESS   read-only
    STATUS       current
    DESCRIPTION
        "Cisco Firepower equipment:FanModule:serial managed
        object property"
    ::= { cfprEquipmentFanModuleEntry 16 }

cfprEquipmentFanModuleThermal OBJECT-TYPE
    SYNTAX       CfprEquipmentSensorThresholdStatus
    MAX-ACCESS   read-only
    STATUS       current
    DESCRIPTION
        "Cisco Firepower equipment:FanModule:thermal managed
        object property"
    ::= { cfprEquipmentFanModuleEntry 17 }

cfprEquipmentFanModuleTray OBJECT-TYPE
    SYNTAX       CfprEquipmentFanModuleTray
    MAX-ACCESS   read-only
    STATUS       current
    DESCRIPTION
        "Cisco Firepower equipment:FanModule:tray managed object property"
    ::= { cfprEquipmentFanModuleEntry 18 }

cfprEquipmentFanModuleVendor OBJECT-TYPE
    SYNTAX       SnmpAdminString
    MAX-ACCESS   read-only
    STATUS       current
    DESCRIPTION
        "Cisco Firepower equipment:FanModule:vendor managed
        object property"
    ::= { cfprEquipmentFanModuleEntry 19 }

cfprEquipmentFanModuleVid OBJECT-TYPE
    SYNTAX       SnmpAdminString
    MAX-ACCESS   read-only
    STATUS       current
    DESCRIPTION
        "Cisco Firepower equipment:FanModule:vid managed object property"
    ::= { cfprEquipmentFanModuleEntry 20 }

cfprEquipmentFanModuleVoltage OBJECT-TYPE
    SYNTAX       CfprEquipmentSensorThresholdStatus
    MAX-ACCESS   read-only
    STATUS       current
    DESCRIPTION
        "Cisco Firepower equipment:FanModule:voltage managed
        object property"
    ::= { cfprEquipmentFanModuleEntry 21 }

cfprEquipmentFanModuleCapProviderTable OBJECT-TYPE
    SYNTAX           SEQUENCE OF CfprEquipmentFanModuleCapProviderEntry
    MAX-ACCESS       not-accessible
    STATUS           current
    DESCRIPTION
        "Cisco Firepower equipment:FanModuleCapProvider
        managed object table"
    ::= { cfprEquipmentObjects 36 }

cfprEquipmentFanModuleCapProviderEntry OBJECT-TYPE
    SYNTAX           CfprEquipmentFanModuleCapProviderEntry
    MAX-ACCESS       not-accessible
    STATUS           current
    DESCRIPTION
        "Entry for the cfprEquipmentFanModuleCapProviderTable table."
    INDEX { cfprEquipmentFanModuleCapProviderInstanceId }
    ::= { cfprEquipmentFanModuleCapProviderTable 1 }

CfprEquipmentFanModuleCapProviderEntry ::= SEQUENCE {
    cfprEquipmentFanModuleCapProviderInstanceId                      CfprManagedObjectId,
    cfprEquipmentFanModuleCapProviderDn                              CfprManagedObjectDn,
    cfprEquipmentFanModuleCapProviderRn                              SnmpAdminString,
    cfprEquipmentFanModuleCapProviderDeleted                         TruthValue,
    cfprEquipmentFanModuleCapProviderDeprecated                      TruthValue,
    cfprEquipmentFanModuleCapProviderElementLoadFailures             Gauge32,
    cfprEquipmentFanModuleCapProviderElementsLoaded                  Gauge32,
    cfprEquipmentFanModuleCapProviderGencount                        Gauge32,
    cfprEquipmentFanModuleCapProviderLoadErrors                      Gauge32,
    cfprEquipmentFanModuleCapProviderLoadWarnings                    Gauge32,
    cfprEquipmentFanModuleCapProviderMgmtPlaneVer                    SnmpAdminString,
    cfprEquipmentFanModuleCapProviderModel                           SnmpAdminString,
    cfprEquipmentFanModuleCapProviderPromCardType                    Gauge32,
    cfprEquipmentFanModuleCapProviderRevision                        SnmpAdminString,
    cfprEquipmentFanModuleCapProviderVendor                          SnmpAdminString
}

cfprEquipmentFanModuleCapProviderInstanceId OBJECT-TYPE
    SYNTAX       CfprManagedObjectId
    MAX-ACCESS   not-accessible
    STATUS       current
    DESCRIPTION
        "Instance identifier of the managed object."
    ::= { cfprEquipmentFanModuleCapProviderEntry 1 }

cfprEquipmentFanModuleCapProviderDn OBJECT-TYPE
    SYNTAX       CfprManagedObjectDn
    MAX-ACCESS   read-only
    STATUS       current
    DESCRIPTION
        "Cisco Firepower equipment:FanModuleCapProvider:dn
        managed object property"
    ::= { cfprEquipmentFanModuleCapProviderEntry 2 }

cfprEquipmentFanModuleCapProviderRn OBJECT-TYPE
    SYNTAX       SnmpAdminString
    MAX-ACCESS   read-only
    STATUS       current
    DESCRIPTION
        "Cisco Firepower equipment:FanModuleCapProvider:rn
        managed object property"
    ::= { cfprEquipmentFanModuleCapProviderEntry 3 }

cfprEquipmentFanModuleCapProviderDeleted OBJECT-TYPE
    SYNTAX       TruthValue
    MAX-ACCESS   read-only
    STATUS       current
    DESCRIPTION
        "Cisco Firepower equipment:FanModuleCapProvider:deleted
        managed object property"
    ::= { cfprEquipmentFanModuleCapProviderEntry 4 }

cfprEquipmentFanModuleCapProviderDeprecated OBJECT-TYPE
    SYNTAX       TruthValue
    MAX-ACCESS   read-only
    STATUS       current
    DESCRIPTION
        "Cisco Firepower equipment:FanModuleCapProvider:deprecated
        managed object property"
    ::= { cfprEquipmentFanModuleCapProviderEntry 5 }

cfprEquipmentFanModuleCapProviderElementLoadFailures OBJECT-TYPE
    SYNTAX       Gauge32
    MAX-ACCESS   read-only
    STATUS       current
    DESCRIPTION
        "Cisco Firepower equipment:FanModuleCapProvider:elementLoadFailure
        s managed object property"
    ::= { cfprEquipmentFanModuleCapProviderEntry 6 }

cfprEquipmentFanModuleCapProviderElementsLoaded OBJECT-TYPE
    SYNTAX       Gauge32
    MAX-ACCESS   read-only
    STATUS       current
    DESCRIPTION
        "Cisco Firepower equipment:FanModuleCapProvider:elementsLoaded
        managed object property"
    ::= { cfprEquipmentFanModuleCapProviderEntry 7 }

cfprEquipmentFanModuleCapProviderGencount OBJECT-TYPE
    SYNTAX       Gauge32
    MAX-ACCESS   read-only
    STATUS       current
    DESCRIPTION
        "Cisco Firepower equipment:FanModuleCapProvider:gencount
        managed object property"
    ::= { cfprEquipmentFanModuleCapProviderEntry 8 }

cfprEquipmentFanModuleCapProviderLoadErrors OBJECT-TYPE
    SYNTAX       Gauge32
    MAX-ACCESS   read-only
    STATUS       current
    DESCRIPTION
        "Cisco Firepower equipment:FanModuleCapProvider:loadErrors
        managed object property"
    ::= { cfprEquipmentFanModuleCapProviderEntry 9 }

cfprEquipmentFanModuleCapProviderLoadWarnings OBJECT-TYPE
    SYNTAX       Gauge32
    MAX-ACCESS   read-only
    STATUS       current
    DESCRIPTION
        "Cisco Firepower equipment:FanModuleCapProvider:loadWarnings
        managed object property"
    ::= { cfprEquipmentFanModuleCapProviderEntry 10 }

cfprEquipmentFanModuleCapProviderMgmtPlaneVer OBJECT-TYPE
    SYNTAX       SnmpAdminString
    MAX-ACCESS   read-only
    STATUS       current
    DESCRIPTION
        "Cisco Firepower equipment:FanModuleCapProvider:mgmtPlaneVer
        managed object property"
    ::= { cfprEquipmentFanModuleCapProviderEntry 11 }

cfprEquipmentFanModuleCapProviderModel OBJECT-TYPE
    SYNTAX       SnmpAdminString
    MAX-ACCESS   read-only
    STATUS       current
    DESCRIPTION
        "Cisco Firepower equipment:FanModuleCapProvider:model
        managed object property"
    ::= { cfprEquipmentFanModuleCapProviderEntry 12 }

cfprEquipmentFanModuleCapProviderPromCardType OBJECT-TYPE
    SYNTAX       Gauge32
    MAX-ACCESS   read-only
    STATUS       current
    DESCRIPTION
        "Cisco Firepower equipment:FanModuleCapProvider:promCardType
        managed object property"
    ::= { cfprEquipmentFanModuleCapProviderEntry 13 }

cfprEquipmentFanModuleCapProviderRevision OBJECT-TYPE
    SYNTAX       SnmpAdminString
    MAX-ACCESS   read-only
    STATUS       current
    DESCRIPTION
        "Cisco Firepower equipment:FanModuleCapProvider:revision
        managed object property"
    ::= { cfprEquipmentFanModuleCapProviderEntry 14 }

cfprEquipmentFanModuleCapProviderVendor OBJECT-TYPE
    SYNTAX       SnmpAdminString
    MAX-ACCESS   read-only
    STATUS       current
    DESCRIPTION
        "Cisco Firepower equipment:FanModuleCapProvider:vendor
        managed object property"
    ::= { cfprEquipmentFanModuleCapProviderEntry 15 }

cfprEquipmentFanModuleDefTable OBJECT-TYPE
    SYNTAX           SEQUENCE OF CfprEquipmentFanModuleDefEntry
    MAX-ACCESS       not-accessible
    STATUS           current
    DESCRIPTION
        "Cisco Firepower equipment:FanModuleDef managed object table"
    ::= { cfprEquipmentObjects 37 }

cfprEquipmentFanModuleDefEntry OBJECT-TYPE
    SYNTAX           CfprEquipmentFanModuleDefEntry
    MAX-ACCESS       not-accessible
    STATUS           current
    DESCRIPTION
        "Entry for the cfprEquipmentFanModuleDefTable table."
    INDEX { cfprEquipmentFanModuleDefInstanceId }
    ::= { cfprEquipmentFanModuleDefTable 1 }

CfprEquipmentFanModuleDefEntry ::= SEQUENCE {
    cfprEquipmentFanModuleDefInstanceId                              CfprManagedObjectId,
    cfprEquipmentFanModuleDefDn                                      CfprManagedObjectDn,
    cfprEquipmentFanModuleDefRn                                      SnmpAdminString,
    cfprEquipmentFanModuleDefDescr                                   SnmpAdminString,
    cfprEquipmentFanModuleDefFanCapacity                             Gauge32,
    cfprEquipmentFanModuleDefIntId                                   SnmpAdminString,
    cfprEquipmentFanModuleDefName                                    SnmpAdminString,
    cfprEquipmentFanModuleDefPolicyLevel                             Gauge32,
    cfprEquipmentFanModuleDefPolicyOwner                             CfprPolicyPolicyOwner
}

cfprEquipmentFanModuleDefInstanceId OBJECT-TYPE
    SYNTAX       CfprManagedObjectId
    MAX-ACCESS   not-accessible
    STATUS       current
    DESCRIPTION
        "Instance identifier of the managed object."
    ::= { cfprEquipmentFanModuleDefEntry 1 }

cfprEquipmentFanModuleDefDn OBJECT-TYPE
    SYNTAX       CfprManagedObjectDn
    MAX-ACCESS   read-only
    STATUS       current
    DESCRIPTION
        "Cisco Firepower equipment:FanModuleDef:dn managed
        object property"
    ::= { cfprEquipmentFanModuleDefEntry 2 }

cfprEquipmentFanModuleDefRn OBJECT-TYPE
    SYNTAX       SnmpAdminString
    MAX-ACCESS   read-only
    STATUS       current
    DESCRIPTION
        "Cisco Firepower equipment:FanModuleDef:rn managed
        object property"
    ::= { cfprEquipmentFanModuleDefEntry 3 }

cfprEquipmentFanModuleDefDescr OBJECT-TYPE
    SYNTAX       SnmpAdminString
    MAX-ACCESS   read-only
    STATUS       current
    DESCRIPTION
        "Cisco Firepower equipment:FanModuleDef:descr managed
        object property"
    ::= { cfprEquipmentFanModuleDefEntry 4 }

cfprEquipmentFanModuleDefFanCapacity OBJECT-TYPE
    SYNTAX       Gauge32
    MAX-ACCESS   read-only
    STATUS       current
    DESCRIPTION
        "Cisco Firepower equipment:FanModuleDef:fanCapacity
        managed object property"
    ::= { cfprEquipmentFanModuleDefEntry 5 }

cfprEquipmentFanModuleDefIntId OBJECT-TYPE
    SYNTAX       SnmpAdminString
    MAX-ACCESS   read-only
    STATUS       current
    DESCRIPTION
        "Cisco Firepower equipment:FanModuleDef:intId managed
        object property"
    ::= { cfprEquipmentFanModuleDefEntry 6 }

cfprEquipmentFanModuleDefName OBJECT-TYPE
    SYNTAX       SnmpAdminString
    MAX-ACCESS   read-only
    STATUS       current
    DESCRIPTION
        "Cisco Firepower equipment:FanModuleDef:name managed
        object property"
    ::= { cfprEquipmentFanModuleDefEntry 7 }

cfprEquipmentFanModuleDefPolicyLevel OBJECT-TYPE
    SYNTAX       Gauge32
    MAX-ACCESS   read-only
    STATUS       current
    DESCRIPTION
        "Cisco Firepower equipment:FanModuleDef:policyLevel
        managed object property"
    ::= { cfprEquipmentFanModuleDefEntry 8 }

cfprEquipmentFanModuleDefPolicyOwner OBJECT-TYPE
    SYNTAX       CfprPolicyPolicyOwner
    MAX-ACCESS   read-only
    STATUS       current
    DESCRIPTION
        "Cisco Firepower equipment:FanModuleDef:policyOwner
        managed object property"
    ::= { cfprEquipmentFanModuleDefEntry 9 }

cfprEquipmentFanModuleStatsTable OBJECT-TYPE
    SYNTAX           SEQUENCE OF CfprEquipmentFanModuleStatsEntry
    MAX-ACCESS       not-accessible
    STATUS           current
    DESCRIPTION
        "Cisco Firepower equipment:FanModuleStats managed object table"
    ::= { cfprEquipmentObjects 38 }

cfprEquipmentFanModuleStatsEntry OBJECT-TYPE
    SYNTAX           CfprEquipmentFanModuleStatsEntry
    MAX-ACCESS       not-accessible
    STATUS           current
    DESCRIPTION
        "Entry for the cfprEquipmentFanModuleStatsTable table."
    INDEX { cfprEquipmentFanModuleStatsInstanceId }
    ::= { cfprEquipmentFanModuleStatsTable 1 }

CfprEquipmentFanModuleStatsEntry ::= SEQUENCE {
    cfprEquipmentFanModuleStatsInstanceId                            CfprManagedObjectId,
    cfprEquipmentFanModuleStatsDn                                    CfprManagedObjectDn,
    cfprEquipmentFanModuleStatsRn                                    SnmpAdminString,
    cfprEquipmentFanModuleStatsAmbientTemp                           INTEGER,
    cfprEquipmentFanModuleStatsAmbientTempAvg                        INTEGER,
    cfprEquipmentFanModuleStatsAmbientTempMax                        INTEGER,
    cfprEquipmentFanModuleStatsAmbientTempMin                        INTEGER,
    cfprEquipmentFanModuleStatsIntervals                             Gauge32,
    cfprEquipmentFanModuleStatsSuspect                               TruthValue,
    cfprEquipmentFanModuleStatsThresholded                           CfprEquipmentFanModuleStatsThresholded,
    cfprEquipmentFanModuleStatsTimeCollected                         DateAndTime,
    cfprEquipmentFanModuleStatsUpdate                                Gauge32
}

cfprEquipmentFanModuleStatsInstanceId OBJECT-TYPE
    SYNTAX       CfprManagedObjectId
    MAX-ACCESS   not-accessible
    STATUS       current
    DESCRIPTION
        "Instance identifier of the managed object."
    ::= { cfprEquipmentFanModuleStatsEntry 1 }

cfprEquipmentFanModuleStatsDn OBJECT-TYPE
    SYNTAX       CfprManagedObjectDn
    MAX-ACCESS   read-only
    STATUS       current
    DESCRIPTION
        "Cisco Firepower equipment:FanModuleStats:dn managed
        object property"
    ::= { cfprEquipmentFanModuleStatsEntry 2 }

cfprEquipmentFanModuleStatsRn OBJECT-TYPE
    SYNTAX       SnmpAdminString
    MAX-ACCESS   read-only
    STATUS       current
    DESCRIPTION
        "Cisco Firepower equipment:FanModuleStats:rn managed
        object property"
    ::= { cfprEquipmentFanModuleStatsEntry 3 }

cfprEquipmentFanModuleStatsAmbientTemp OBJECT-TYPE
    SYNTAX       INTEGER
    MAX-ACCESS   read-only
    STATUS       current
    DESCRIPTION
        "Cisco Firepower equipment:FanModuleStats:ambientTemp
        managed object property"
    ::= { cfprEquipmentFanModuleStatsEntry 4 }

cfprEquipmentFanModuleStatsAmbientTempAvg OBJECT-TYPE
    SYNTAX       INTEGER
    MAX-ACCESS   read-only
    STATUS       current
    DESCRIPTION
        "Cisco Firepower equipment:FanModuleStats:ambientTempAvg
        managed object property"
    ::= { cfprEquipmentFanModuleStatsEntry 5 }

cfprEquipmentFanModuleStatsAmbientTempMax OBJECT-TYPE
    SYNTAX       INTEGER
    MAX-ACCESS   read-only
    STATUS       current
    DESCRIPTION
        "Cisco Firepower equipment:FanModuleStats:ambientTempMax
        managed object property"
    ::= { cfprEquipmentFanModuleStatsEntry 6 }

cfprEquipmentFanModuleStatsAmbientTempMin OBJECT-TYPE
    SYNTAX       INTEGER
    MAX-ACCESS   read-only
    STATUS       current
    DESCRIPTION
        "Cisco Firepower equipment:FanModuleStats:ambientTempMin
        managed object property"
    ::= { cfprEquipmentFanModuleStatsEntry 7 }

cfprEquipmentFanModuleStatsIntervals OBJECT-TYPE
    SYNTAX       Gauge32
    MAX-ACCESS   read-only
    STATUS       current
    DESCRIPTION
        "Cisco Firepower equipment:FanModuleStats:intervals
        managed object property"
    ::= { cfprEquipmentFanModuleStatsEntry 8 }

cfprEquipmentFanModuleStatsSuspect OBJECT-TYPE
    SYNTAX       TruthValue
    MAX-ACCESS   read-only
    STATUS       current
    DESCRIPTION
        "Cisco Firepower equipment:FanModuleStats:suspect
        managed object property"
    ::= { cfprEquipmentFanModuleStatsEntry 9 }

cfprEquipmentFanModuleStatsThresholded OBJECT-TYPE
    SYNTAX       CfprEquipmentFanModuleStatsThresholded
    MAX-ACCESS   read-only
    STATUS       current
    DESCRIPTION
        "Cisco Firepower equipment:FanModuleStats:thresholded
        managed object property"
    ::= { cfprEquipmentFanModuleStatsEntry 10 }

cfprEquipmentFanModuleStatsTimeCollected OBJECT-TYPE
    SYNTAX       DateAndTime
    MAX-ACCESS   read-only
    STATUS       current
    DESCRIPTION
        "Cisco Firepower equipment:FanModuleStats:timeCollected
        managed object property"
    ::= { cfprEquipmentFanModuleStatsEntry 11 }

cfprEquipmentFanModuleStatsUpdate OBJECT-TYPE
    SYNTAX       Gauge32
    MAX-ACCESS   read-only
    STATUS       current
    DESCRIPTION
        "Cisco Firepower equipment:FanModuleStats:update
        managed object property"
    ::= { cfprEquipmentFanModuleStatsEntry 12 }

cfprEquipmentFanModuleStatsHistTable OBJECT-TYPE
    SYNTAX           SEQUENCE OF CfprEquipmentFanModuleStatsHistEntry
    MAX-ACCESS       not-accessible
    STATUS           current
    DESCRIPTION
        "Cisco Firepower equipment:FanModuleStatsHist managed
        object table"
    ::= { cfprEquipmentObjects 39 }

cfprEquipmentFanModuleStatsHistEntry OBJECT-TYPE
    SYNTAX           CfprEquipmentFanModuleStatsHistEntry
    MAX-ACCESS       not-accessible
    STATUS           current
    DESCRIPTION
        "Entry for the cfprEquipmentFanModuleStatsHistTable table."
    INDEX { cfprEquipmentFanModuleStatsHistInstanceId }
    ::= { cfprEquipmentFanModuleStatsHistTable 1 }

CfprEquipmentFanModuleStatsHistEntry ::= SEQUENCE {
    cfprEquipmentFanModuleStatsHistInstanceId                        CfprManagedObjectId,
    cfprEquipmentFanModuleStatsHistDn                                CfprManagedObjectDn,
    cfprEquipmentFanModuleStatsHistRn                                SnmpAdminString,
    cfprEquipmentFanModuleStatsHistAmbientTemp                       INTEGER,
    cfprEquipmentFanModuleStatsHistAmbientTempAvg                    INTEGER,
    cfprEquipmentFanModuleStatsHistAmbientTempMax                    INTEGER,
    cfprEquipmentFanModuleStatsHistAmbientTempMin                    INTEGER,
    cfprEquipmentFanModuleStatsHistId                                Unsigned64,
    cfprEquipmentFanModuleStatsHistMostRecent                        TruthValue,
    cfprEquipmentFanModuleStatsHistSuspect                           TruthValue,
    cfprEquipmentFanModuleStatsHistThresholded                       CfprEquipmentFanModuleStatsHistThresholded,
    cfprEquipmentFanModuleStatsHistTimeCollected                     DateAndTime
}

cfprEquipmentFanModuleStatsHistInstanceId OBJECT-TYPE
    SYNTAX       CfprManagedObjectId
    MAX-ACCESS   not-accessible
    STATUS       current
    DESCRIPTION
        "Instance identifier of the managed object."
    ::= { cfprEquipmentFanModuleStatsHistEntry 1 }

cfprEquipmentFanModuleStatsHistDn OBJECT-TYPE
    SYNTAX       CfprManagedObjectDn
    MAX-ACCESS   read-only
    STATUS       current
    DESCRIPTION
        "Cisco Firepower equipment:FanModuleStatsHist:dn
        managed object property"
    ::= { cfprEquipmentFanModuleStatsHistEntry 2 }

cfprEquipmentFanModuleStatsHistRn OBJECT-TYPE
    SYNTAX       SnmpAdminString
    MAX-ACCESS   read-only
    STATUS       current
    DESCRIPTION
        "Cisco Firepower equipment:FanModuleStatsHist:rn
        managed object property"
    ::= { cfprEquipmentFanModuleStatsHistEntry 3 }

cfprEquipmentFanModuleStatsHistAmbientTemp OBJECT-TYPE
    SYNTAX       INTEGER
    MAX-ACCESS   read-only
    STATUS       current
    DESCRIPTION
        "Cisco Firepower equipment:FanModuleStatsHist:ambientTemp
        managed object property"
    ::= { cfprEquipmentFanModuleStatsHistEntry 4 }

cfprEquipmentFanModuleStatsHistAmbientTempAvg OBJECT-TYPE
    SYNTAX       INTEGER
    MAX-ACCESS   read-only
    STATUS       current
    DESCRIPTION
        "Cisco Firepower equipment:FanModuleStatsHist:ambientTempAvg
        managed object property"
    ::= { cfprEquipmentFanModuleStatsHistEntry 5 }

cfprEquipmentFanModuleStatsHistAmbientTempMax OBJECT-TYPE
    SYNTAX       INTEGER
    MAX-ACCESS   read-only
    STATUS       current
    DESCRIPTION
        "Cisco Firepower equipment:FanModuleStatsHist:ambientTempMax
        managed object property"
    ::= { cfprEquipmentFanModuleStatsHistEntry 6 }

cfprEquipmentFanModuleStatsHistAmbientTempMin OBJECT-TYPE
    SYNTAX       INTEGER
    MAX-ACCESS   read-only
    STATUS       current
    DESCRIPTION
        "Cisco Firepower equipment:FanModuleStatsHist:ambientTempMin
        managed object property"
    ::= { cfprEquipmentFanModuleStatsHistEntry 7 }

cfprEquipmentFanModuleStatsHistId OBJECT-TYPE
    SYNTAX       Unsigned64
    MAX-ACCESS   read-only
    STATUS       current
    DESCRIPTION
        "Cisco Firepower equipment:FanModuleStatsHist:id
        managed object property"
    ::= { cfprEquipmentFanModuleStatsHistEntry 8 }

cfprEquipmentFanModuleStatsHistMostRecent OBJECT-TYPE
    SYNTAX       TruthValue
    MAX-ACCESS   read-only
    STATUS       current
    DESCRIPTION
        "Cisco Firepower equipment:FanModuleStatsHist:mostRecent
        managed object property"
    ::= { cfprEquipmentFanModuleStatsHistEntry 9 }

cfprEquipmentFanModuleStatsHistSuspect OBJECT-TYPE
    SYNTAX       TruthValue
    MAX-ACCESS   read-only
    STATUS       current
    DESCRIPTION
        "Cisco Firepower equipment:FanModuleStatsHist:suspect
        managed object property"
    ::= { cfprEquipmentFanModuleStatsHistEntry 10 }

cfprEquipmentFanModuleStatsHistThresholded OBJECT-TYPE
    SYNTAX       CfprEquipmentFanModuleStatsHistThresholded
    MAX-ACCESS   read-only
    STATUS       current
    DESCRIPTION
        "Cisco Firepower equipment:FanModuleStatsHist:thresholded
        managed object property"
    ::= { cfprEquipmentFanModuleStatsHistEntry 11 }

cfprEquipmentFanModuleStatsHistTimeCollected OBJECT-TYPE
    SYNTAX       DateAndTime
    MAX-ACCESS   read-only
    STATUS       current
    DESCRIPTION
        "Cisco Firepower equipment:FanModuleStatsHist:timeCollected
        managed object property"
    ::= { cfprEquipmentFanModuleStatsHistEntry 12 }

cfprEquipmentFanStatsTable OBJECT-TYPE
    SYNTAX           SEQUENCE OF CfprEquipmentFanStatsEntry
    MAX-ACCESS       not-accessible
    STATUS           current
    DESCRIPTION
        "Cisco Firepower equipment:FanStats managed object table"
    ::= { cfprEquipmentObjects 40 }

cfprEquipmentFanStatsEntry OBJECT-TYPE
    SYNTAX           CfprEquipmentFanStatsEntry
    MAX-ACCESS       not-accessible
    STATUS           current
    DESCRIPTION
        "Entry for the cfprEquipmentFanStatsTable table."
    INDEX { cfprEquipmentFanStatsInstanceId }
    ::= { cfprEquipmentFanStatsTable 1 }

CfprEquipmentFanStatsEntry ::= SEQUENCE {
    cfprEquipmentFanStatsInstanceId                                  CfprManagedObjectId,
    cfprEquipmentFanStatsDn                                          CfprManagedObjectDn,
    cfprEquipmentFanStatsRn                                          SnmpAdminString,
    cfprEquipmentFanStatsIntervals                                   Gauge32,
    cfprEquipmentFanStatsSpeed                                       Gauge32,
    cfprEquipmentFanStatsSpeedAvg                                    Gauge32,
    cfprEquipmentFanStatsSpeedMax                                    Gauge32,
    cfprEquipmentFanStatsSpeedMin                                    Gauge32,
    cfprEquipmentFanStatsSuspect                                     TruthValue,
    cfprEquipmentFanStatsThresholded                                 CfprEquipmentFanStatsThresholded,
    cfprEquipmentFanStatsTimeCollected                               DateAndTime,
    cfprEquipmentFanStatsUpdate                                      Gauge32
}

cfprEquipmentFanStatsInstanceId OBJECT-TYPE
    SYNTAX       CfprManagedObjectId
    MAX-ACCESS   not-accessible
    STATUS       current
    DESCRIPTION
        "Instance identifier of the managed object."
    ::= { cfprEquipmentFanStatsEntry 1 }

cfprEquipmentFanStatsDn OBJECT-TYPE
    SYNTAX       CfprManagedObjectDn
    MAX-ACCESS   read-only
    STATUS       current
    DESCRIPTION
        "Cisco Firepower equipment:FanStats:dn managed object property"
    ::= { cfprEquipmentFanStatsEntry 2 }

cfprEquipmentFanStatsRn OBJECT-TYPE
    SYNTAX       SnmpAdminString
    MAX-ACCESS   read-only
    STATUS       current
    DESCRIPTION
        "Cisco Firepower equipment:FanStats:rn managed object property"
    ::= { cfprEquipmentFanStatsEntry 3 }

cfprEquipmentFanStatsIntervals OBJECT-TYPE
    SYNTAX       Gauge32
    MAX-ACCESS   read-only
    STATUS       current
    DESCRIPTION
        "Cisco Firepower equipment:FanStats:intervals managed
        object property"
    ::= { cfprEquipmentFanStatsEntry 4 }

cfprEquipmentFanStatsSpeed OBJECT-TYPE
    SYNTAX       Gauge32
    MAX-ACCESS   read-only
    STATUS       current
    DESCRIPTION
        "Cisco Firepower equipment:FanStats:speed managed object property"
    ::= { cfprEquipmentFanStatsEntry 5 }

cfprEquipmentFanStatsSpeedAvg OBJECT-TYPE
    SYNTAX       Gauge32
    MAX-ACCESS   read-only
    STATUS       current
    DESCRIPTION
        "Cisco Firepower equipment:FanStats:speedAvg managed
        object property"
    ::= { cfprEquipmentFanStatsEntry 6 }

cfprEquipmentFanStatsSpeedMax OBJECT-TYPE
    SYNTAX       Gauge32
    MAX-ACCESS   read-only
    STATUS       current
    DESCRIPTION
        "Cisco Firepower equipment:FanStats:speedMax managed
        object property"
    ::= { cfprEquipmentFanStatsEntry 7 }

cfprEquipmentFanStatsSpeedMin OBJECT-TYPE
    SYNTAX       Gauge32
    MAX-ACCESS   read-only
    STATUS       current
    DESCRIPTION
        "Cisco Firepower equipment:FanStats:speedMin managed
        object property"
    ::= { cfprEquipmentFanStatsEntry 8 }

cfprEquipmentFanStatsSuspect OBJECT-TYPE
    SYNTAX       TruthValue
    MAX-ACCESS   read-only
    STATUS       current
    DESCRIPTION
        "Cisco Firepower equipment:FanStats:suspect managed
        object property"
    ::= { cfprEquipmentFanStatsEntry 9 }

cfprEquipmentFanStatsThresholded OBJECT-TYPE
    SYNTAX       CfprEquipmentFanStatsThresholded
    MAX-ACCESS   read-only
    STATUS       current
    DESCRIPTION
        "Cisco Firepower equipment:FanStats:thresholded
        managed object property"
    ::= { cfprEquipmentFanStatsEntry 10 }

cfprEquipmentFanStatsTimeCollected OBJECT-TYPE
    SYNTAX       DateAndTime
    MAX-ACCESS   read-only
    STATUS       current
    DESCRIPTION
        "Cisco Firepower equipment:FanStats:timeCollected
        managed object property"
    ::= { cfprEquipmentFanStatsEntry 11 }

cfprEquipmentFanStatsUpdate OBJECT-TYPE
    SYNTAX       Gauge32
    MAX-ACCESS   read-only
    STATUS       current
    DESCRIPTION
        "Cisco Firepower equipment:FanStats:update managed
        object property"
    ::= { cfprEquipmentFanStatsEntry 12 }

cfprEquipmentFanStatsHistTable OBJECT-TYPE
    SYNTAX           SEQUENCE OF CfprEquipmentFanStatsHistEntry
    MAX-ACCESS       not-accessible
    STATUS           current
    DESCRIPTION
        "Cisco Firepower equipment:FanStatsHist managed object table"
    ::= { cfprEquipmentObjects 41 }

cfprEquipmentFanStatsHistEntry OBJECT-TYPE
    SYNTAX           CfprEquipmentFanStatsHistEntry
    MAX-ACCESS       not-accessible
    STATUS           current
    DESCRIPTION
        "Entry for the cfprEquipmentFanStatsHistTable table."
    INDEX { cfprEquipmentFanStatsHistInstanceId }
    ::= { cfprEquipmentFanStatsHistTable 1 }

CfprEquipmentFanStatsHistEntry ::= SEQUENCE {
    cfprEquipmentFanStatsHistInstanceId                              CfprManagedObjectId,
    cfprEquipmentFanStatsHistDn                                      CfprManagedObjectDn,
    cfprEquipmentFanStatsHistRn                                      SnmpAdminString,
    cfprEquipmentFanStatsHistId                                      Unsigned64,
    cfprEquipmentFanStatsHistMostRecent                              TruthValue,
    cfprEquipmentFanStatsHistSpeed                                   Gauge32,
    cfprEquipmentFanStatsHistSpeedAvg                                Gauge32,
    cfprEquipmentFanStatsHistSpeedMax                                Gauge32,
    cfprEquipmentFanStatsHistSpeedMin                                Gauge32,
    cfprEquipmentFanStatsHistSuspect                                 TruthValue,
    cfprEquipmentFanStatsHistThresholded                             CfprEquipmentFanStatsHistThresholded,
    cfprEquipmentFanStatsHistTimeCollected                           DateAndTime
}

cfprEquipmentFanStatsHistInstanceId OBJECT-TYPE
    SYNTAX       CfprManagedObjectId
    MAX-ACCESS   not-accessible
    STATUS       current
    DESCRIPTION
        "Instance identifier of the managed object."
    ::= { cfprEquipmentFanStatsHistEntry 1 }

cfprEquipmentFanStatsHistDn OBJECT-TYPE
    SYNTAX       CfprManagedObjectDn
    MAX-ACCESS   read-only
    STATUS       current
    DESCRIPTION
        "Cisco Firepower equipment:FanStatsHist:dn managed
        object property"
    ::= { cfprEquipmentFanStatsHistEntry 2 }

cfprEquipmentFanStatsHistRn OBJECT-TYPE
    SYNTAX       SnmpAdminString
    MAX-ACCESS   read-only
    STATUS       current
    DESCRIPTION
        "Cisco Firepower equipment:FanStatsHist:rn managed
        object property"
    ::= { cfprEquipmentFanStatsHistEntry 3 }

cfprEquipmentFanStatsHistId OBJECT-TYPE
    SYNTAX       Unsigned64
    MAX-ACCESS   read-only
    STATUS       current
    DESCRIPTION
        "Cisco Firepower equipment:FanStatsHist:id managed
        object property"
    ::= { cfprEquipmentFanStatsHistEntry 4 }

cfprEquipmentFanStatsHistMostRecent OBJECT-TYPE
    SYNTAX       TruthValue
    MAX-ACCESS   read-only
    STATUS       current
    DESCRIPTION
        "Cisco Firepower equipment:FanStatsHist:mostRecent
        managed object property"
    ::= { cfprEquipmentFanStatsHistEntry 5 }

cfprEquipmentFanStatsHistSpeed OBJECT-TYPE
    SYNTAX       Gauge32
    MAX-ACCESS   read-only
    STATUS       current
    DESCRIPTION
        "Cisco Firepower equipment:FanStatsHist:speed managed
        object property"
    ::= { cfprEquipmentFanStatsHistEntry 6 }

cfprEquipmentFanStatsHistSpeedAvg OBJECT-TYPE
    SYNTAX       Gauge32
    MAX-ACCESS   read-only
    STATUS       current
    DESCRIPTION
        "Cisco Firepower equipment:FanStatsHist:speedAvg
        managed object property"
    ::= { cfprEquipmentFanStatsHistEntry 7 }

cfprEquipmentFanStatsHistSpeedMax OBJECT-TYPE
    SYNTAX       Gauge32
    MAX-ACCESS   read-only
    STATUS       current
    DESCRIPTION
        "Cisco Firepower equipment:FanStatsHist:speedMax
        managed object property"
    ::= { cfprEquipmentFanStatsHistEntry 8 }

cfprEquipmentFanStatsHistSpeedMin OBJECT-TYPE
    SYNTAX       Gauge32
    MAX-ACCESS   read-only
    STATUS       current
    DESCRIPTION
        "Cisco Firepower equipment:FanStatsHist:speedMin
        managed object property"
    ::= { cfprEquipmentFanStatsHistEntry 9 }

cfprEquipmentFanStatsHistSuspect OBJECT-TYPE
    SYNTAX       TruthValue
    MAX-ACCESS   read-only
    STATUS       current
    DESCRIPTION
        "Cisco Firepower equipment:FanStatsHist:suspect
        managed object property"
    ::= { cfprEquipmentFanStatsHistEntry 10 }

cfprEquipmentFanStatsHistThresholded OBJECT-TYPE
    SYNTAX       CfprEquipmentFanStatsHistThresholded
    MAX-ACCESS   read-only
    STATUS       current
    DESCRIPTION
        "Cisco Firepower equipment:FanStatsHist:thresholded
        managed object property"
    ::= { cfprEquipmentFanStatsHistEntry 11 }

cfprEquipmentFanStatsHistTimeCollected OBJECT-TYPE
    SYNTAX       DateAndTime
    MAX-ACCESS   read-only
    STATUS       current
    DESCRIPTION
        "Cisco Firepower equipment:FanStatsHist:timeCollected
        managed object property"
    ::= { cfprEquipmentFanStatsHistEntry 12 }

cfprEquipmentFexTable OBJECT-TYPE
    SYNTAX           SEQUENCE OF CfprEquipmentFexEntry
    MAX-ACCESS       not-accessible
    STATUS           current
    DESCRIPTION
        "Cisco Firepower equipment:Fex managed object table"
    ::= { cfprEquipmentObjects 42 }

cfprEquipmentFexEntry OBJECT-TYPE
    SYNTAX           CfprEquipmentFexEntry
    MAX-ACCESS       not-accessible
    STATUS           current
    DESCRIPTION
        "Entry for the cfprEquipmentFexTable table."
    INDEX { cfprEquipmentFexInstanceId }
    ::= { cfprEquipmentFexTable 1 }

CfprEquipmentFexEntry ::= SEQUENCE {
    cfprEquipmentFexInstanceId                                       CfprManagedObjectId,
    cfprEquipmentFexDn                                               CfprManagedObjectDn,
    cfprEquipmentFexRn                                               SnmpAdminString,
    cfprEquipmentFexAdminPowerState                                  CfprEquipmentAdminPowerState,
    cfprEquipmentFexAdminState                                       CfprEquipmentChassisAdminState,
    cfprEquipmentFexConfigState                                      CfprEquipmentChassisConfigState,
    cfprEquipmentFexFltAggr                                          Unsigned64,
    cfprEquipmentFexFsmDescr                                         SnmpAdminString,
    cfprEquipmentFexFsmPrev                                          SnmpAdminString,
    cfprEquipmentFexFsmProgr                                         Gauge32,
    cfprEquipmentFexFsmRmtInvErrCode                                 Gauge32,
    cfprEquipmentFexFsmRmtInvErrDescr                                SnmpAdminString,
    cfprEquipmentFexFsmRmtInvRslt                                    CfprConditionRemoteInvRslt,
    cfprEquipmentFexFsmStageDescr                                    SnmpAdminString,
    cfprEquipmentFexFsmStamp                                         DateAndTime,
    cfprEquipmentFexFsmStatus                                        SnmpAdminString,
    cfprEquipmentFexFsmTry                                           Gauge32,
    cfprEquipmentFexId                                               CfprEquipmentFexId,
    cfprEquipmentFexLicGP                                            Unsigned64,
    cfprEquipmentFexLicState                                         CfprLicenseState,
    cfprEquipmentFexModel                                            SnmpAdminString,
    cfprEquipmentFexOperQualifier                                    CfprEquipmentChassisIssues,
    cfprEquipmentFexOperQualifierReason                              SnmpAdminString,
    cfprEquipmentFexOperState                                        CfprEquipmentOperability,
    cfprEquipmentFexOperability                                      CfprEquipmentOperability,
    cfprEquipmentFexPower                                            CfprEquipmentPowerState,
    cfprEquipmentFexPresence                                         CfprEquipmentPresence,
    cfprEquipmentFexRevision                                         SnmpAdminString,
    cfprEquipmentFexSerial                                           SnmpAdminString,
    cfprEquipmentFexSwitchId                                         CfprNetworkSwitchId,
    cfprEquipmentFexThermal                                          CfprEquipmentSensorThresholdStatus,
    cfprEquipmentFexUsrLbl                                           SnmpAdminString,
    cfprEquipmentFexVendor                                           SnmpAdminString,
    cfprEquipmentFexVoltage                                          CfprEquipmentSensorThresholdStatus
}

cfprEquipmentFexInstanceId OBJECT-TYPE
    SYNTAX       CfprManagedObjectId
    MAX-ACCESS   not-accessible
    STATUS       current
    DESCRIPTION
        "Instance identifier of the managed object."
    ::= { cfprEquipmentFexEntry 1 }

cfprEquipmentFexDn OBJECT-TYPE
    SYNTAX       CfprManagedObjectDn
    MAX-ACCESS   read-only
    STATUS       current
    DESCRIPTION
        "Cisco Firepower equipment:Fex:dn managed object property"
    ::= { cfprEquipmentFexEntry 2 }

cfprEquipmentFexRn OBJECT-TYPE
    SYNTAX       SnmpAdminString
    MAX-ACCESS   read-only
    STATUS       current
    DESCRIPTION
        "Cisco Firepower equipment:Fex:rn managed object property"
    ::= { cfprEquipmentFexEntry 3 }

cfprEquipmentFexAdminPowerState OBJECT-TYPE
    SYNTAX       CfprEquipmentAdminPowerState
    MAX-ACCESS   read-only
    STATUS       current
    DESCRIPTION
        "Cisco Firepower equipment:Fex:adminPowerState
        managed object property"
    ::= { cfprEquipmentFexEntry 4 }

cfprEquipmentFexAdminState OBJECT-TYPE
    SYNTAX       CfprEquipmentChassisAdminState
    MAX-ACCESS   read-only
    STATUS       current
    DESCRIPTION
        "Cisco Firepower equipment:Fex:adminState managed object property"
    ::= { cfprEquipmentFexEntry 5 }

cfprEquipmentFexConfigState OBJECT-TYPE
    SYNTAX       CfprEquipmentChassisConfigState
    MAX-ACCESS   read-only
    STATUS       current
    DESCRIPTION
        "Cisco Firepower equipment:Fex:configState managed
        object property"
    ::= { cfprEquipmentFexEntry 6 }

cfprEquipmentFexFltAggr OBJECT-TYPE
    SYNTAX       Unsigned64
    MAX-ACCESS   read-only
    STATUS       current
    DESCRIPTION
        "Cisco Firepower equipment:Fex:fltAggr managed object property"
    ::= { cfprEquipmentFexEntry 7 }

cfprEquipmentFexFsmDescr OBJECT-TYPE
    SYNTAX       SnmpAdminString
    MAX-ACCESS   read-only
    STATUS       current
    DESCRIPTION
        "Cisco Firepower equipment:Fex:fsmDescr managed object property"
    ::= { cfprEquipmentFexEntry 8 }

cfprEquipmentFexFsmPrev OBJECT-TYPE
    SYNTAX       SnmpAdminString
    MAX-ACCESS   read-only
    STATUS       current
    DESCRIPTION
        "Cisco Firepower equipment:Fex:fsmPrev managed object property"
    ::= { cfprEquipmentFexEntry 9 }

cfprEquipmentFexFsmProgr OBJECT-TYPE
    SYNTAX       Gauge32
    MAX-ACCESS   read-only
    STATUS       current
    DESCRIPTION
        "Cisco Firepower equipment:Fex:fsmProgr managed object property"
    ::= { cfprEquipmentFexEntry 10 }

cfprEquipmentFexFsmRmtInvErrCode OBJECT-TYPE
    SYNTAX       Gauge32
    MAX-ACCESS   read-only
    STATUS       current
    DESCRIPTION
        "Cisco Firepower equipment:Fex:fsmRmtInvErrCode
        managed object property"
    ::= { cfprEquipmentFexEntry 11 }

cfprEquipmentFexFsmRmtInvErrDescr OBJECT-TYPE
    SYNTAX       SnmpAdminString
    MAX-ACCESS   read-only
    STATUS       current
    DESCRIPTION
        "Cisco Firepower equipment:Fex:fsmRmtInvErrDescr
        managed object property"
    ::= { cfprEquipmentFexEntry 12 }

cfprEquipmentFexFsmRmtInvRslt OBJECT-TYPE
    SYNTAX       CfprConditionRemoteInvRslt
    MAX-ACCESS   read-only
    STATUS       current
    DESCRIPTION
        "Cisco Firepower equipment:Fex:fsmRmtInvRslt managed
        object property"
    ::= { cfprEquipmentFexEntry 13 }

cfprEquipmentFexFsmStageDescr OBJECT-TYPE
    SYNTAX       SnmpAdminString
    MAX-ACCESS   read-only
    STATUS       current
    DESCRIPTION
        "Cisco Firepower equipment:Fex:fsmStageDescr managed
        object property"
    ::= { cfprEquipmentFexEntry 14 }

cfprEquipmentFexFsmStamp OBJECT-TYPE
    SYNTAX       DateAndTime
    MAX-ACCESS   read-only
    STATUS       current
    DESCRIPTION
        "Cisco Firepower equipment:Fex:fsmStamp managed object property"
    ::= { cfprEquipmentFexEntry 15 }

cfprEquipmentFexFsmStatus OBJECT-TYPE
    SYNTAX       SnmpAdminString
    MAX-ACCESS   read-only
    STATUS       current
    DESCRIPTION
        "Cisco Firepower equipment:Fex:fsmStatus managed object property"
    ::= { cfprEquipmentFexEntry 16 }

cfprEquipmentFexFsmTry OBJECT-TYPE
    SYNTAX       Gauge32
    MAX-ACCESS   read-only
    STATUS       current
    DESCRIPTION
        "Cisco Firepower equipment:Fex:fsmTry managed object property"
    ::= { cfprEquipmentFexEntry 17 }

cfprEquipmentFexId OBJECT-TYPE
    SYNTAX       CfprEquipmentFexId
    MAX-ACCESS   read-only
    STATUS       current
    DESCRIPTION
        "Cisco Firepower equipment:Fex:id managed object property"
    ::= { cfprEquipmentFexEntry 18 }

cfprEquipmentFexLicGP OBJECT-TYPE
    SYNTAX       Unsigned64
    MAX-ACCESS   read-only
    STATUS       current
    DESCRIPTION
        "Cisco Firepower equipment:Fex:licGP managed object property"
    ::= { cfprEquipmentFexEntry 19 }

cfprEquipmentFexLicState OBJECT-TYPE
    SYNTAX       CfprLicenseState
    MAX-ACCESS   read-only
    STATUS       current
    DESCRIPTION
        "Cisco Firepower equipment:Fex:licState managed object property"
    ::= { cfprEquipmentFexEntry 20 }

cfprEquipmentFexModel OBJECT-TYPE
    SYNTAX       SnmpAdminString
    MAX-ACCESS   read-only
    STATUS       current
    DESCRIPTION
        "Cisco Firepower equipment:Fex:model managed object property"
    ::= { cfprEquipmentFexEntry 21 }

cfprEquipmentFexOperQualifier OBJECT-TYPE
    SYNTAX       CfprEquipmentChassisIssues
    MAX-ACCESS   read-only
    STATUS       current
    DESCRIPTION
        "Cisco Firepower equipment:Fex:operQualifier managed
        object property"
    ::= { cfprEquipmentFexEntry 22 }

cfprEquipmentFexOperQualifierReason OBJECT-TYPE
    SYNTAX       SnmpAdminString
    MAX-ACCESS   read-only
    STATUS       current
    DESCRIPTION
        "Cisco Firepower equipment:Fex:operQualifierReason
        managed object property"
    ::= { cfprEquipmentFexEntry 23 }

cfprEquipmentFexOperState OBJECT-TYPE
    SYNTAX       CfprEquipmentOperability
    MAX-ACCESS   read-only
    STATUS       current
    DESCRIPTION
        "Cisco Firepower equipment:Fex:operState managed object property"
    ::= { cfprEquipmentFexEntry 24 }

cfprEquipmentFexOperability OBJECT-TYPE
    SYNTAX       CfprEquipmentOperability
    MAX-ACCESS   read-only
    STATUS       current
    DESCRIPTION
        "Cisco Firepower equipment:Fex:operability managed
        object property"
    ::= { cfprEquipmentFexEntry 25 }

cfprEquipmentFexPower OBJECT-TYPE
    SYNTAX       CfprEquipmentPowerState
    MAX-ACCESS   read-only
    STATUS       current
    DESCRIPTION
        "Cisco Firepower equipment:Fex:power managed object property"
    ::= { cfprEquipmentFexEntry 26 }

cfprEquipmentFexPresence OBJECT-TYPE
    SYNTAX       CfprEquipmentPresence
    MAX-ACCESS   read-only
    STATUS       current
    DESCRIPTION
        "Cisco Firepower equipment:Fex:presence managed object property"
    ::= { cfprEquipmentFexEntry 27 }

cfprEquipmentFexRevision OBJECT-TYPE
    SYNTAX       SnmpAdminString
    MAX-ACCESS   read-only
    STATUS       current
    DESCRIPTION
        "Cisco Firepower equipment:Fex:revision managed object property"
    ::= { cfprEquipmentFexEntry 28 }

cfprEquipmentFexSerial OBJECT-TYPE
    SYNTAX       SnmpAdminString
    MAX-ACCESS   read-only
    STATUS       current
    DESCRIPTION
        "Cisco Firepower equipment:Fex:serial managed object property"
    ::= { cfprEquipmentFexEntry 29 }

cfprEquipmentFexSwitchId OBJECT-TYPE
    SYNTAX       CfprNetworkSwitchId
    MAX-ACCESS   read-only
    STATUS       current
    DESCRIPTION
        "Cisco Firepower equipment:Fex:switchId managed object property"
    ::= { cfprEquipmentFexEntry 30 }

cfprEquipmentFexThermal OBJECT-TYPE
    SYNTAX       CfprEquipmentSensorThresholdStatus
    MAX-ACCESS   read-only
    STATUS       current
    DESCRIPTION
        "Cisco Firepower equipment:Fex:thermal managed object property"
    ::= { cfprEquipmentFexEntry 31 }

cfprEquipmentFexUsrLbl OBJECT-TYPE
    SYNTAX       SnmpAdminString
    MAX-ACCESS   read-only
    STATUS       current
    DESCRIPTION
        "Cisco Firepower equipment:Fex:usrLbl managed object property"
    ::= { cfprEquipmentFexEntry 32 }

cfprEquipmentFexVendor OBJECT-TYPE
    SYNTAX       SnmpAdminString
    MAX-ACCESS   read-only
    STATUS       current
    DESCRIPTION
        "Cisco Firepower equipment:Fex:vendor managed object property"
    ::= { cfprEquipmentFexEntry 33 }

cfprEquipmentFexVoltage OBJECT-TYPE
    SYNTAX       CfprEquipmentSensorThresholdStatus
    MAX-ACCESS   read-only
    STATUS       current
    DESCRIPTION
        "Cisco Firepower equipment:Fex:voltage managed object property"
    ::= { cfprEquipmentFexEntry 34 }

cfprEquipmentFexCapProviderTable OBJECT-TYPE
    SYNTAX           SEQUENCE OF CfprEquipmentFexCapProviderEntry
    MAX-ACCESS       not-accessible
    STATUS           current
    DESCRIPTION
        "Cisco Firepower equipment:FexCapProvider managed object table"
    ::= { cfprEquipmentObjects 43 }

cfprEquipmentFexCapProviderEntry OBJECT-TYPE
    SYNTAX           CfprEquipmentFexCapProviderEntry
    MAX-ACCESS       not-accessible
    STATUS           current
    DESCRIPTION
        "Entry for the cfprEquipmentFexCapProviderTable table."
    INDEX { cfprEquipmentFexCapProviderInstanceId }
    ::= { cfprEquipmentFexCapProviderTable 1 }

CfprEquipmentFexCapProviderEntry ::= SEQUENCE {
    cfprEquipmentFexCapProviderInstanceId                            CfprManagedObjectId,
    cfprEquipmentFexCapProviderDn                                    CfprManagedObjectDn,
    cfprEquipmentFexCapProviderRn                                    SnmpAdminString,
    cfprEquipmentFexCapProviderDeleted                               TruthValue,
    cfprEquipmentFexCapProviderDeprecated                            TruthValue,
    cfprEquipmentFexCapProviderElementLoadFailures                   Gauge32,
    cfprEquipmentFexCapProviderElementsLoaded                        Gauge32,
    cfprEquipmentFexCapProviderGencount                              Gauge32,
    cfprEquipmentFexCapProviderLoadErrors                            Gauge32,
    cfprEquipmentFexCapProviderLoadWarnings                          Gauge32,
    cfprEquipmentFexCapProviderMgmtPlaneVer                          SnmpAdminString,
    cfprEquipmentFexCapProviderModel                                 SnmpAdminString,
    cfprEquipmentFexCapProviderPromCardType                          Gauge32,
    cfprEquipmentFexCapProviderRevision                              SnmpAdminString,
    cfprEquipmentFexCapProviderRole                                  CfprEquipmentFexCapProviderRole,
    cfprEquipmentFexCapProviderVendor                                SnmpAdminString
}

cfprEquipmentFexCapProviderInstanceId OBJECT-TYPE
    SYNTAX       CfprManagedObjectId
    MAX-ACCESS   not-accessible
    STATUS       current
    DESCRIPTION
        "Instance identifier of the managed object."
    ::= { cfprEquipmentFexCapProviderEntry 1 }

cfprEquipmentFexCapProviderDn OBJECT-TYPE
    SYNTAX       CfprManagedObjectDn
    MAX-ACCESS   read-only
    STATUS       current
    DESCRIPTION
        "Cisco Firepower equipment:FexCapProvider:dn managed
        object property"
    ::= { cfprEquipmentFexCapProviderEntry 2 }

cfprEquipmentFexCapProviderRn OBJECT-TYPE
    SYNTAX       SnmpAdminString
    MAX-ACCESS   read-only
    STATUS       current
    DESCRIPTION
        "Cisco Firepower equipment:FexCapProvider:rn managed
        object property"
    ::= { cfprEquipmentFexCapProviderEntry 3 }

cfprEquipmentFexCapProviderDeleted OBJECT-TYPE
    SYNTAX       TruthValue
    MAX-ACCESS   read-only
    STATUS       current
    DESCRIPTION
        "Cisco Firepower equipment:FexCapProvider:deleted
        managed object property"
    ::= { cfprEquipmentFexCapProviderEntry 4 }

cfprEquipmentFexCapProviderDeprecated OBJECT-TYPE
    SYNTAX       TruthValue
    MAX-ACCESS   read-only
    STATUS       current
    DESCRIPTION
        "Cisco Firepower equipment:FexCapProvider:deprecated
        managed object property"
    ::= { cfprEquipmentFexCapProviderEntry 5 }

cfprEquipmentFexCapProviderElementLoadFailures OBJECT-TYPE
    SYNTAX       Gauge32
    MAX-ACCESS   read-only
    STATUS       current
    DESCRIPTION
        "Cisco Firepower equipment:FexCapProvider:elementLoadFailures
        managed object property"
    ::= { cfprEquipmentFexCapProviderEntry 6 }

cfprEquipmentFexCapProviderElementsLoaded OBJECT-TYPE
    SYNTAX       Gauge32
    MAX-ACCESS   read-only
    STATUS       current
    DESCRIPTION
        "Cisco Firepower equipment:FexCapProvider:elementsLoaded
        managed object property"
    ::= { cfprEquipmentFexCapProviderEntry 7 }

cfprEquipmentFexCapProviderGencount OBJECT-TYPE
    SYNTAX       Gauge32
    MAX-ACCESS   read-only
    STATUS       current
    DESCRIPTION
        "Cisco Firepower equipment:FexCapProvider:gencount
        managed object property"
    ::= { cfprEquipmentFexCapProviderEntry 8 }

cfprEquipmentFexCapProviderLoadErrors OBJECT-TYPE
    SYNTAX       Gauge32
    MAX-ACCESS   read-only
    STATUS       current
    DESCRIPTION
        "Cisco Firepower equipment:FexCapProvider:loadErrors
        managed object property"
    ::= { cfprEquipmentFexCapProviderEntry 9 }

cfprEquipmentFexCapProviderLoadWarnings OBJECT-TYPE
    SYNTAX       Gauge32
    MAX-ACCESS   read-only
    STATUS       current
    DESCRIPTION
        "Cisco Firepower equipment:FexCapProvider:loadWarnings
        managed object property"
    ::= { cfprEquipmentFexCapProviderEntry 10 }

cfprEquipmentFexCapProviderMgmtPlaneVer OBJECT-TYPE
    SYNTAX       SnmpAdminString
    MAX-ACCESS   read-only
    STATUS       current
    DESCRIPTION
        "Cisco Firepower equipment:FexCapProvider:mgmtPlaneVer
        managed object property"
    ::= { cfprEquipmentFexCapProviderEntry 11 }

cfprEquipmentFexCapProviderModel OBJECT-TYPE
    SYNTAX       SnmpAdminString
    MAX-ACCESS   read-only
    STATUS       current
    DESCRIPTION
        "Cisco Firepower equipment:FexCapProvider:model
        managed object property"
    ::= { cfprEquipmentFexCapProviderEntry 12 }

cfprEquipmentFexCapProviderPromCardType OBJECT-TYPE
    SYNTAX       Gauge32
    MAX-ACCESS   read-only
    STATUS       current
    DESCRIPTION
        "Cisco Firepower equipment:FexCapProvider:promCardType
        managed object property"
    ::= { cfprEquipmentFexCapProviderEntry 13 }

cfprEquipmentFexCapProviderRevision OBJECT-TYPE
    SYNTAX       SnmpAdminString
    MAX-ACCESS   read-only
    STATUS       current
    DESCRIPTION
        "Cisco Firepower equipment:FexCapProvider:revision
        managed object property"
    ::= { cfprEquipmentFexCapProviderEntry 14 }

cfprEquipmentFexCapProviderRole OBJECT-TYPE
    SYNTAX       CfprEquipmentFexCapProviderRole
    MAX-ACCESS   read-only
    STATUS       current
    DESCRIPTION
        "Cisco Firepower equipment:FexCapProvider:role
        managed object property"
    ::= { cfprEquipmentFexCapProviderEntry 15 }

cfprEquipmentFexCapProviderVendor OBJECT-TYPE
    SYNTAX       SnmpAdminString
    MAX-ACCESS   read-only
    STATUS       current
    DESCRIPTION
        "Cisco Firepower equipment:FexCapProvider:vendor
        managed object property"
    ::= { cfprEquipmentFexCapProviderEntry 16 }

cfprEquipmentFexEnvStatsTable OBJECT-TYPE
    SYNTAX           SEQUENCE OF CfprEquipmentFexEnvStatsEntry
    MAX-ACCESS       not-accessible
    STATUS           current
    DESCRIPTION
        "Cisco Firepower equipment:FexEnvStats managed object table"
    ::= { cfprEquipmentObjects 44 }

cfprEquipmentFexEnvStatsEntry OBJECT-TYPE
    SYNTAX           CfprEquipmentFexEnvStatsEntry
    MAX-ACCESS       not-accessible
    STATUS           current
    DESCRIPTION
        "Entry for the cfprEquipmentFexEnvStatsTable table."
    INDEX { cfprEquipmentFexEnvStatsInstanceId }
    ::= { cfprEquipmentFexEnvStatsTable 1 }

CfprEquipmentFexEnvStatsEntry ::= SEQUENCE {
    cfprEquipmentFexEnvStatsInstanceId                               CfprManagedObjectId,
    cfprEquipmentFexEnvStatsDn                                       CfprManagedObjectDn,
    cfprEquipmentFexEnvStatsRn                                       SnmpAdminString,
    cfprEquipmentFexEnvStatsDie1                                     INTEGER,
    cfprEquipmentFexEnvStatsDie1Avg                                  INTEGER,
    cfprEquipmentFexEnvStatsDie1Max                                  INTEGER,
    cfprEquipmentFexEnvStatsDie1Min                                  INTEGER,
    cfprEquipmentFexEnvStatsInlet                                    INTEGER,
    cfprEquipmentFexEnvStatsInlet1                                   INTEGER,
    cfprEquipmentFexEnvStatsInlet1Avg                                INTEGER,
    cfprEquipmentFexEnvStatsInlet1Max                                INTEGER,
    cfprEquipmentFexEnvStatsInlet1Min                                INTEGER,
    cfprEquipmentFexEnvStatsInletAvg                                 INTEGER,
    cfprEquipmentFexEnvStatsInletMax                                 INTEGER,
    cfprEquipmentFexEnvStatsInletMin                                 INTEGER,
    cfprEquipmentFexEnvStatsInputStatus                              SnmpAdminString,
    cfprEquipmentFexEnvStatsIntervals                                Gauge32,
    cfprEquipmentFexEnvStatsOutlet1                                  INTEGER,
    cfprEquipmentFexEnvStatsOutlet1Avg                               INTEGER,
    cfprEquipmentFexEnvStatsOutlet1Max                               INTEGER,
    cfprEquipmentFexEnvStatsOutlet1Min                               INTEGER,
    cfprEquipmentFexEnvStatsOutlet2                                  INTEGER,
    cfprEquipmentFexEnvStatsOutlet2Avg                               INTEGER,
    cfprEquipmentFexEnvStatsOutlet2Max                               INTEGER,
    cfprEquipmentFexEnvStatsOutlet2Min                               INTEGER,
    cfprEquipmentFexEnvStatsSuspect                                  TruthValue,
    cfprEquipmentFexEnvStatsThresholded                              CfprEquipmentFexEnvStatsThresholded,
    cfprEquipmentFexEnvStatsTimeCollected                            DateAndTime,
    cfprEquipmentFexEnvStatsUpdate                                   Gauge32
}

cfprEquipmentFexEnvStatsInstanceId OBJECT-TYPE
    SYNTAX       CfprManagedObjectId
    MAX-ACCESS   not-accessible
    STATUS       current
    DESCRIPTION
        "Instance identifier of the managed object."
    ::= { cfprEquipmentFexEnvStatsEntry 1 }

cfprEquipmentFexEnvStatsDn OBJECT-TYPE
    SYNTAX       CfprManagedObjectDn
    MAX-ACCESS   read-only
    STATUS       current
    DESCRIPTION
        "Cisco Firepower equipment:FexEnvStats:dn managed object property"
    ::= { cfprEquipmentFexEnvStatsEntry 2 }

cfprEquipmentFexEnvStatsRn OBJECT-TYPE
    SYNTAX       SnmpAdminString
    MAX-ACCESS   read-only
    STATUS       current
    DESCRIPTION
        "Cisco Firepower equipment:FexEnvStats:rn managed object property"
    ::= { cfprEquipmentFexEnvStatsEntry 3 }

cfprEquipmentFexEnvStatsDie1 OBJECT-TYPE
    SYNTAX       INTEGER
    MAX-ACCESS   read-only
    STATUS       current
    DESCRIPTION
        "Cisco Firepower equipment:FexEnvStats:die1 managed
        object property"
    ::= { cfprEquipmentFexEnvStatsEntry 4 }

cfprEquipmentFexEnvStatsDie1Avg OBJECT-TYPE
    SYNTAX       INTEGER
    MAX-ACCESS   read-only
    STATUS       current
    DESCRIPTION
        "Cisco Firepower equipment:FexEnvStats:die1Avg
        managed object property"
    ::= { cfprEquipmentFexEnvStatsEntry 5 }

cfprEquipmentFexEnvStatsDie1Max OBJECT-TYPE
    SYNTAX       INTEGER
    MAX-ACCESS   read-only
    STATUS       current
    DESCRIPTION
        "Cisco Firepower equipment:FexEnvStats:die1Max
        managed object property"
    ::= { cfprEquipmentFexEnvStatsEntry 6 }

cfprEquipmentFexEnvStatsDie1Min OBJECT-TYPE
    SYNTAX       INTEGER
    MAX-ACCESS   read-only
    STATUS       current
    DESCRIPTION
        "Cisco Firepower equipment:FexEnvStats:die1Min
        managed object property"
    ::= { cfprEquipmentFexEnvStatsEntry 7 }

cfprEquipmentFexEnvStatsInlet OBJECT-TYPE
    SYNTAX       INTEGER
    MAX-ACCESS   read-only
    STATUS       current
    DESCRIPTION
        "Cisco Firepower equipment:FexEnvStats:inlet managed
        object property"
    ::= { cfprEquipmentFexEnvStatsEntry 8 }

cfprEquipmentFexEnvStatsInlet1 OBJECT-TYPE
    SYNTAX       INTEGER
    MAX-ACCESS   read-only
    STATUS       current
    DESCRIPTION
        "Cisco Firepower equipment:FexEnvStats:inlet1 managed
        object property"
    ::= { cfprEquipmentFexEnvStatsEntry 9 }

cfprEquipmentFexEnvStatsInlet1Avg OBJECT-TYPE
    SYNTAX       INTEGER
    MAX-ACCESS   read-only
    STATUS       current
    DESCRIPTION
        "Cisco Firepower equipment:FexEnvStats:inlet1Avg
        managed object property"
    ::= { cfprEquipmentFexEnvStatsEntry 10 }

cfprEquipmentFexEnvStatsInlet1Max OBJECT-TYPE
    SYNTAX       INTEGER
    MAX-ACCESS   read-only
    STATUS       current
    DESCRIPTION
        "Cisco Firepower equipment:FexEnvStats:inlet1Max
        managed object property"
    ::= { cfprEquipmentFexEnvStatsEntry 11 }

cfprEquipmentFexEnvStatsInlet1Min OBJECT-TYPE
    SYNTAX       INTEGER
    MAX-ACCESS   read-only
    STATUS       current
    DESCRIPTION
        "Cisco Firepower equipment:FexEnvStats:inlet1Min
        managed object property"
    ::= { cfprEquipmentFexEnvStatsEntry 12 }

cfprEquipmentFexEnvStatsInletAvg OBJECT-TYPE
    SYNTAX       INTEGER
    MAX-ACCESS   read-only
    STATUS       current
    DESCRIPTION
        "Cisco Firepower equipment:FexEnvStats:inletAvg
        managed object property"
    ::= { cfprEquipmentFexEnvStatsEntry 13 }

cfprEquipmentFexEnvStatsInletMax OBJECT-TYPE
    SYNTAX       INTEGER
    MAX-ACCESS   read-only
    STATUS       current
    DESCRIPTION
        "Cisco Firepower equipment:FexEnvStats:inletMax
        managed object property"
    ::= { cfprEquipmentFexEnvStatsEntry 14 }

cfprEquipmentFexEnvStatsInletMin OBJECT-TYPE
    SYNTAX       INTEGER
    MAX-ACCESS   read-only
    STATUS       current
    DESCRIPTION
        "Cisco Firepower equipment:FexEnvStats:inletMin
        managed object property"
    ::= { cfprEquipmentFexEnvStatsEntry 15 }

cfprEquipmentFexEnvStatsInputStatus OBJECT-TYPE
    SYNTAX       SnmpAdminString
    MAX-ACCESS   read-only
    STATUS       current
    DESCRIPTION
        "Cisco Firepower equipment:FexEnvStats:inputStatus
        managed object property"
    ::= { cfprEquipmentFexEnvStatsEntry 16 }

cfprEquipmentFexEnvStatsIntervals OBJECT-TYPE
    SYNTAX       Gauge32
    MAX-ACCESS   read-only
    STATUS       current
    DESCRIPTION
        "Cisco Firepower equipment:FexEnvStats:intervals
        managed object property"
    ::= { cfprEquipmentFexEnvStatsEntry 17 }

cfprEquipmentFexEnvStatsOutlet1 OBJECT-TYPE
    SYNTAX       INTEGER
    MAX-ACCESS   read-only
    STATUS       current
    DESCRIPTION
        "Cisco Firepower equipment:FexEnvStats:outlet1
        managed object property"
    ::= { cfprEquipmentFexEnvStatsEntry 18 }

cfprEquipmentFexEnvStatsOutlet1Avg OBJECT-TYPE
    SYNTAX       INTEGER
    MAX-ACCESS   read-only
    STATUS       current
    DESCRIPTION
        "Cisco Firepower equipment:FexEnvStats:outlet1Avg
        managed object property"
    ::= { cfprEquipmentFexEnvStatsEntry 19 }

cfprEquipmentFexEnvStatsOutlet1Max OBJECT-TYPE
    SYNTAX       INTEGER
    MAX-ACCESS   read-only
    STATUS       current
    DESCRIPTION
        "Cisco Firepower equipment:FexEnvStats:outlet1Max
        managed object property"
    ::= { cfprEquipmentFexEnvStatsEntry 20 }

cfprEquipmentFexEnvStatsOutlet1Min OBJECT-TYPE
    SYNTAX       INTEGER
    MAX-ACCESS   read-only
    STATUS       current
    DESCRIPTION
        "Cisco Firepower equipment:FexEnvStats:outlet1Min
        managed object property"
    ::= { cfprEquipmentFexEnvStatsEntry 21 }

cfprEquipmentFexEnvStatsOutlet2 OBJECT-TYPE
    SYNTAX       INTEGER
    MAX-ACCESS   read-only
    STATUS       current
    DESCRIPTION
        "Cisco Firepower equipment:FexEnvStats:outlet2
        managed object property"
    ::= { cfprEquipmentFexEnvStatsEntry 22 }

cfprEquipmentFexEnvStatsOutlet2Avg OBJECT-TYPE
    SYNTAX       INTEGER
    MAX-ACCESS   read-only
    STATUS       current
    DESCRIPTION
        "Cisco Firepower equipment:FexEnvStats:outlet2Avg
        managed object property"
    ::= { cfprEquipmentFexEnvStatsEntry 23 }

cfprEquipmentFexEnvStatsOutlet2Max OBJECT-TYPE
    SYNTAX       INTEGER
    MAX-ACCESS   read-only
    STATUS       current
    DESCRIPTION
        "Cisco Firepower equipment:FexEnvStats:outlet2Max
        managed object property"
    ::= { cfprEquipmentFexEnvStatsEntry 24 }

cfprEquipmentFexEnvStatsOutlet2Min OBJECT-TYPE
    SYNTAX       INTEGER
    MAX-ACCESS   read-only
    STATUS       current
    DESCRIPTION
        "Cisco Firepower equipment:FexEnvStats:outlet2Min
        managed object property"
    ::= { cfprEquipmentFexEnvStatsEntry 25 }

cfprEquipmentFexEnvStatsSuspect OBJECT-TYPE
    SYNTAX       TruthValue
    MAX-ACCESS   read-only
    STATUS       current
    DESCRIPTION
        "Cisco Firepower equipment:FexEnvStats:suspect
        managed object property"
    ::= { cfprEquipmentFexEnvStatsEntry 26 }

cfprEquipmentFexEnvStatsThresholded OBJECT-TYPE
    SYNTAX       CfprEquipmentFexEnvStatsThresholded
    MAX-ACCESS   read-only
    STATUS       current
    DESCRIPTION
        "Cisco Firepower equipment:FexEnvStats:thresholded
        managed object property"
    ::= { cfprEquipmentFexEnvStatsEntry 27 }

cfprEquipmentFexEnvStatsTimeCollected OBJECT-TYPE
    SYNTAX       DateAndTime
    MAX-ACCESS   read-only
    STATUS       current
    DESCRIPTION
        "Cisco Firepower equipment:FexEnvStats:timeCollected
        managed object property"
    ::= { cfprEquipmentFexEnvStatsEntry 28 }

cfprEquipmentFexEnvStatsUpdate OBJECT-TYPE
    SYNTAX       Gauge32
    MAX-ACCESS   read-only
    STATUS       current
    DESCRIPTION
        "Cisco Firepower equipment:FexEnvStats:update managed
        object property"
    ::= { cfprEquipmentFexEnvStatsEntry 29 }

cfprEquipmentFexEnvStatsHistTable OBJECT-TYPE
    SYNTAX           SEQUENCE OF CfprEquipmentFexEnvStatsHistEntry
    MAX-ACCESS       not-accessible
    STATUS           current
    DESCRIPTION
        "Cisco Firepower equipment:FexEnvStatsHist managed object table"
    ::= { cfprEquipmentObjects 45 }

cfprEquipmentFexEnvStatsHistEntry OBJECT-TYPE
    SYNTAX           CfprEquipmentFexEnvStatsHistEntry
    MAX-ACCESS       not-accessible
    STATUS           current
    DESCRIPTION
        "Entry for the cfprEquipmentFexEnvStatsHistTable table."
    INDEX { cfprEquipmentFexEnvStatsHistInstanceId }
    ::= { cfprEquipmentFexEnvStatsHistTable 1 }

CfprEquipmentFexEnvStatsHistEntry ::= SEQUENCE {
    cfprEquipmentFexEnvStatsHistInstanceId                           CfprManagedObjectId,
    cfprEquipmentFexEnvStatsHistDn                                   CfprManagedObjectDn,
    cfprEquipmentFexEnvStatsHistRn                                   SnmpAdminString,
    cfprEquipmentFexEnvStatsHistDie1                                 INTEGER,
    cfprEquipmentFexEnvStatsHistDie1Avg                              INTEGER,
    cfprEquipmentFexEnvStatsHistDie1Max                              INTEGER,
    cfprEquipmentFexEnvStatsHistDie1Min                              INTEGER,
    cfprEquipmentFexEnvStatsHistId                                   Unsigned64,
    cfprEquipmentFexEnvStatsHistInlet                                INTEGER,
    cfprEquipmentFexEnvStatsHistInlet1                               INTEGER,
    cfprEquipmentFexEnvStatsHistInlet1Avg                            INTEGER,
    cfprEquipmentFexEnvStatsHistInlet1Max                            INTEGER,
    cfprEquipmentFexEnvStatsHistInlet1Min                            INTEGER,
    cfprEquipmentFexEnvStatsHistInletAvg                             INTEGER,
    cfprEquipmentFexEnvStatsHistInletMax                             INTEGER,
    cfprEquipmentFexEnvStatsHistInletMin                             INTEGER,
    cfprEquipmentFexEnvStatsHistMostRecent                           TruthValue,
    cfprEquipmentFexEnvStatsHistOutlet1                              INTEGER,
    cfprEquipmentFexEnvStatsHistOutlet1Avg                           INTEGER,
    cfprEquipmentFexEnvStatsHistOutlet1Max                           INTEGER,
    cfprEquipmentFexEnvStatsHistOutlet1Min                           INTEGER,
    cfprEquipmentFexEnvStatsHistOutlet2                              INTEGER,
    cfprEquipmentFexEnvStatsHistOutlet2Avg                           INTEGER,
    cfprEquipmentFexEnvStatsHistOutlet2Max                           INTEGER,
    cfprEquipmentFexEnvStatsHistOutlet2Min                           INTEGER,
    cfprEquipmentFexEnvStatsHistSuspect                              TruthValue,
    cfprEquipmentFexEnvStatsHistThresholded                          CfprEquipmentFexEnvStatsHistThresholded,
    cfprEquipmentFexEnvStatsHistTimeCollected                        DateAndTime
}

cfprEquipmentFexEnvStatsHistInstanceId OBJECT-TYPE
    SYNTAX       CfprManagedObjectId
    MAX-ACCESS   not-accessible
    STATUS       current
    DESCRIPTION
        "Instance identifier of the managed object."
    ::= { cfprEquipmentFexEnvStatsHistEntry 1 }

cfprEquipmentFexEnvStatsHistDn OBJECT-TYPE
    SYNTAX       CfprManagedObjectDn
    MAX-ACCESS   read-only
    STATUS       current
    DESCRIPTION
        "Cisco Firepower equipment:FexEnvStatsHist:dn managed
        object property"
    ::= { cfprEquipmentFexEnvStatsHistEntry 2 }

cfprEquipmentFexEnvStatsHistRn OBJECT-TYPE
    SYNTAX       SnmpAdminString
    MAX-ACCESS   read-only
    STATUS       current
    DESCRIPTION
        "Cisco Firepower equipment:FexEnvStatsHist:rn managed
        object property"
    ::= { cfprEquipmentFexEnvStatsHistEntry 3 }

cfprEquipmentFexEnvStatsHistDie1 OBJECT-TYPE
    SYNTAX       INTEGER
    MAX-ACCESS   read-only
    STATUS       current
    DESCRIPTION
        "Cisco Firepower equipment:FexEnvStatsHist:die1
        managed object property"
    ::= { cfprEquipmentFexEnvStatsHistEntry 4 }

cfprEquipmentFexEnvStatsHistDie1Avg OBJECT-TYPE
    SYNTAX       INTEGER
    MAX-ACCESS   read-only
    STATUS       current
    DESCRIPTION
        "Cisco Firepower equipment:FexEnvStatsHist:die1Avg
        managed object property"
    ::= { cfprEquipmentFexEnvStatsHistEntry 5 }

cfprEquipmentFexEnvStatsHistDie1Max OBJECT-TYPE
    SYNTAX       INTEGER
    MAX-ACCESS   read-only
    STATUS       current
    DESCRIPTION
        "Cisco Firepower equipment:FexEnvStatsHist:die1Max
        managed object property"
    ::= { cfprEquipmentFexEnvStatsHistEntry 6 }

cfprEquipmentFexEnvStatsHistDie1Min OBJECT-TYPE
    SYNTAX       INTEGER
    MAX-ACCESS   read-only
    STATUS       current
    DESCRIPTION
        "Cisco Firepower equipment:FexEnvStatsHist:die1Min
        managed object property"
    ::= { cfprEquipmentFexEnvStatsHistEntry 7 }

cfprEquipmentFexEnvStatsHistId OBJECT-TYPE
    SYNTAX       Unsigned64
    MAX-ACCESS   read-only
    STATUS       current
    DESCRIPTION
        "Cisco Firepower equipment:FexEnvStatsHist:id managed
        object property"
    ::= { cfprEquipmentFexEnvStatsHistEntry 8 }

cfprEquipmentFexEnvStatsHistInlet OBJECT-TYPE
    SYNTAX       INTEGER
    MAX-ACCESS   read-only
    STATUS       current
    DESCRIPTION
        "Cisco Firepower equipment:FexEnvStatsHist:inlet
        managed object property"
    ::= { cfprEquipmentFexEnvStatsHistEntry 9 }

cfprEquipmentFexEnvStatsHistInlet1 OBJECT-TYPE
    SYNTAX       INTEGER
    MAX-ACCESS   read-only
    STATUS       current
    DESCRIPTION
        "Cisco Firepower equipment:FexEnvStatsHist:inlet1
        managed object property"
    ::= { cfprEquipmentFexEnvStatsHistEntry 10 }

cfprEquipmentFexEnvStatsHistInlet1Avg OBJECT-TYPE
    SYNTAX       INTEGER
    MAX-ACCESS   read-only
    STATUS       current
    DESCRIPTION
        "Cisco Firepower equipment:FexEnvStatsHist:inlet1Avg
        managed object property"
    ::= { cfprEquipmentFexEnvStatsHistEntry 11 }

cfprEquipmentFexEnvStatsHistInlet1Max OBJECT-TYPE
    SYNTAX       INTEGER
    MAX-ACCESS   read-only
    STATUS       current
    DESCRIPTION
        "Cisco Firepower equipment:FexEnvStatsHist:inlet1Max
        managed object property"
    ::= { cfprEquipmentFexEnvStatsHistEntry 12 }

cfprEquipmentFexEnvStatsHistInlet1Min OBJECT-TYPE
    SYNTAX       INTEGER
    MAX-ACCESS   read-only
    STATUS       current
    DESCRIPTION
        "Cisco Firepower equipment:FexEnvStatsHist:inlet1Min
        managed object property"
    ::= { cfprEquipmentFexEnvStatsHistEntry 13 }

cfprEquipmentFexEnvStatsHistInletAvg OBJECT-TYPE
    SYNTAX       INTEGER
    MAX-ACCESS   read-only
    STATUS       current
    DESCRIPTION
        "Cisco Firepower equipment:FexEnvStatsHist:inletAvg
        managed object property"
    ::= { cfprEquipmentFexEnvStatsHistEntry 14 }

cfprEquipmentFexEnvStatsHistInletMax OBJECT-TYPE
    SYNTAX       INTEGER
    MAX-ACCESS   read-only
    STATUS       current
    DESCRIPTION
        "Cisco Firepower equipment:FexEnvStatsHist:inletMax
        managed object property"
    ::= { cfprEquipmentFexEnvStatsHistEntry 15 }

cfprEquipmentFexEnvStatsHistInletMin OBJECT-TYPE
    SYNTAX       INTEGER
    MAX-ACCESS   read-only
    STATUS       current
    DESCRIPTION
        "Cisco Firepower equipment:FexEnvStatsHist:inletMin
        managed object property"
    ::= { cfprEquipmentFexEnvStatsHistEntry 16 }

cfprEquipmentFexEnvStatsHistMostRecent OBJECT-TYPE
    SYNTAX       TruthValue
    MAX-ACCESS   read-only
    STATUS       current
    DESCRIPTION
        "Cisco Firepower equipment:FexEnvStatsHist:mostRecent
        managed object property"
    ::= { cfprEquipmentFexEnvStatsHistEntry 17 }

cfprEquipmentFexEnvStatsHistOutlet1 OBJECT-TYPE
    SYNTAX       INTEGER
    MAX-ACCESS   read-only
    STATUS       current
    DESCRIPTION
        "Cisco Firepower equipment:FexEnvStatsHist:outlet1
        managed object property"
    ::= { cfprEquipmentFexEnvStatsHistEntry 18 }

cfprEquipmentFexEnvStatsHistOutlet1Avg OBJECT-TYPE
    SYNTAX       INTEGER
    MAX-ACCESS   read-only
    STATUS       current
    DESCRIPTION
        "Cisco Firepower equipment:FexEnvStatsHist:outlet1Avg
        managed object property"
    ::= { cfprEquipmentFexEnvStatsHistEntry 19 }

cfprEquipmentFexEnvStatsHistOutlet1Max OBJECT-TYPE
    SYNTAX       INTEGER
    MAX-ACCESS   read-only
    STATUS       current
    DESCRIPTION
        "Cisco Firepower equipment:FexEnvStatsHist:outlet1Max
        managed object property"
    ::= { cfprEquipmentFexEnvStatsHistEntry 20 }

cfprEquipmentFexEnvStatsHistOutlet1Min OBJECT-TYPE
    SYNTAX       INTEGER
    MAX-ACCESS   read-only
    STATUS       current
    DESCRIPTION
        "Cisco Firepower equipment:FexEnvStatsHist:outlet1Min
        managed object property"
    ::= { cfprEquipmentFexEnvStatsHistEntry 21 }

cfprEquipmentFexEnvStatsHistOutlet2 OBJECT-TYPE
    SYNTAX       INTEGER
    MAX-ACCESS   read-only
    STATUS       current
    DESCRIPTION
        "Cisco Firepower equipment:FexEnvStatsHist:outlet2
        managed object property"
    ::= { cfprEquipmentFexEnvStatsHistEntry 22 }

cfprEquipmentFexEnvStatsHistOutlet2Avg OBJECT-TYPE
    SYNTAX       INTEGER
    MAX-ACCESS   read-only
    STATUS       current
    DESCRIPTION
        "Cisco Firepower equipment:FexEnvStatsHist:outlet2Avg
        managed object property"
    ::= { cfprEquipmentFexEnvStatsHistEntry 23 }

cfprEquipmentFexEnvStatsHistOutlet2Max OBJECT-TYPE
    SYNTAX       INTEGER
    MAX-ACCESS   read-only
    STATUS       current
    DESCRIPTION
        "Cisco Firepower equipment:FexEnvStatsHist:outlet2Max
        managed object property"
    ::= { cfprEquipmentFexEnvStatsHistEntry 24 }

cfprEquipmentFexEnvStatsHistOutlet2Min OBJECT-TYPE
    SYNTAX       INTEGER
    MAX-ACCESS   read-only
    STATUS       current
    DESCRIPTION
        "Cisco Firepower equipment:FexEnvStatsHist:outlet2Min
        managed object property"
    ::= { cfprEquipmentFexEnvStatsHistEntry 25 }

cfprEquipmentFexEnvStatsHistSuspect OBJECT-TYPE
    SYNTAX       TruthValue
    MAX-ACCESS   read-only
    STATUS       current
    DESCRIPTION
        "Cisco Firepower equipment:FexEnvStatsHist:suspect
        managed object property"
    ::= { cfprEquipmentFexEnvStatsHistEntry 26 }

cfprEquipmentFexEnvStatsHistThresholded OBJECT-TYPE
    SYNTAX       CfprEquipmentFexEnvStatsHistThresholded
    MAX-ACCESS   read-only
    STATUS       current
    DESCRIPTION
        "Cisco Firepower equipment:FexEnvStatsHist:thresholded
        managed object property"
    ::= { cfprEquipmentFexEnvStatsHistEntry 27 }

cfprEquipmentFexEnvStatsHistTimeCollected OBJECT-TYPE
    SYNTAX       DateAndTime
    MAX-ACCESS   read-only
    STATUS       current
    DESCRIPTION
        "Cisco Firepower equipment:FexEnvStatsHist:timeCollected
        managed object property"
    ::= { cfprEquipmentFexEnvStatsHistEntry 28 }

cfprEquipmentFexFsmTable OBJECT-TYPE
    SYNTAX           SEQUENCE OF CfprEquipmentFexFsmEntry
    MAX-ACCESS       not-accessible
    STATUS           current
    DESCRIPTION
        "Cisco Firepower equipment:FexFsm managed object table"
    ::= { cfprEquipmentObjects 46 }

cfprEquipmentFexFsmEntry OBJECT-TYPE
    SYNTAX           CfprEquipmentFexFsmEntry
    MAX-ACCESS       not-accessible
    STATUS           current
    DESCRIPTION
        "Entry for the cfprEquipmentFexFsmTable table."
    INDEX { cfprEquipmentFexFsmInstanceId }
    ::= { cfprEquipmentFexFsmTable 1 }

CfprEquipmentFexFsmEntry ::= SEQUENCE {
    cfprEquipmentFexFsmInstanceId                                    CfprManagedObjectId,
    cfprEquipmentFexFsmDn                                            CfprManagedObjectDn,
    cfprEquipmentFexFsmRn                                            SnmpAdminString,
    cfprEquipmentFexFsmCompletionTime                                DateAndTime,
    cfprEquipmentFexFsmCurrentFsm                                    CfprEquipmentFexFsmCurrentFsm,
    cfprEquipmentFexFsmDescrData                                     SnmpAdminString,
    cfprEquipmentFexFsmFsmStatus                                     CfprFsmFsmStageStatus,
    cfprEquipmentFexFsmProgress                                      Gauge32,
    cfprEquipmentFexFsmRmtErrCode                                    Gauge32,
    cfprEquipmentFexFsmRmtErrDescr                                   SnmpAdminString,
    cfprEquipmentFexFsmRmtRslt                                       CfprConditionRemoteInvRslt
}

cfprEquipmentFexFsmInstanceId OBJECT-TYPE
    SYNTAX       CfprManagedObjectId
    MAX-ACCESS   not-accessible
    STATUS       current
    DESCRIPTION
        "Instance identifier of the managed object."
    ::= { cfprEquipmentFexFsmEntry 1 }

cfprEquipmentFexFsmDn OBJECT-TYPE
    SYNTAX       CfprManagedObjectDn
    MAX-ACCESS   read-only
    STATUS       current
    DESCRIPTION
        "Cisco Firepower equipment:FexFsm:dn managed object property"
    ::= { cfprEquipmentFexFsmEntry 2 }

cfprEquipmentFexFsmRn OBJECT-TYPE
    SYNTAX       SnmpAdminString
    MAX-ACCESS   read-only
    STATUS       current
    DESCRIPTION
        "Cisco Firepower equipment:FexFsm:rn managed object property"
    ::= { cfprEquipmentFexFsmEntry 3 }

cfprEquipmentFexFsmCompletionTime OBJECT-TYPE
    SYNTAX       DateAndTime
    MAX-ACCESS   read-only
    STATUS       current
    DESCRIPTION
        "Cisco Firepower equipment:FexFsm:completionTime
        managed object property"
    ::= { cfprEquipmentFexFsmEntry 4 }

cfprEquipmentFexFsmCurrentFsm OBJECT-TYPE
    SYNTAX       CfprEquipmentFexFsmCurrentFsm
    MAX-ACCESS   read-only
    STATUS       current
    DESCRIPTION
        "Cisco Firepower equipment:FexFsm:currentFsm managed
        object property"
    ::= { cfprEquipmentFexFsmEntry 5 }

cfprEquipmentFexFsmDescrData OBJECT-TYPE
    SYNTAX       SnmpAdminString
    MAX-ACCESS   read-only
    STATUS       current
    DESCRIPTION
        "Cisco Firepower equipment:FexFsm:descr managed object property"
    ::= { cfprEquipmentFexFsmEntry 6 }

cfprEquipmentFexFsmFsmStatus OBJECT-TYPE
    SYNTAX       CfprFsmFsmStageStatus
    MAX-ACCESS   read-only
    STATUS       current
    DESCRIPTION
        "Cisco Firepower equipment:FexFsm:fsmStatus managed
        object property"
    ::= { cfprEquipmentFexFsmEntry 7 }

cfprEquipmentFexFsmProgress OBJECT-TYPE
    SYNTAX       Gauge32
    MAX-ACCESS   read-only
    STATUS       current
    DESCRIPTION
        "Cisco Firepower equipment:FexFsm:progress managed
        object property"
    ::= { cfprEquipmentFexFsmEntry 8 }

cfprEquipmentFexFsmRmtErrCode OBJECT-TYPE
    SYNTAX       Gauge32
    MAX-ACCESS   read-only
    STATUS       current
    DESCRIPTION
        "Cisco Firepower equipment:FexFsm:rmtErrCode managed
        object property"
    ::= { cfprEquipmentFexFsmEntry 9 }

cfprEquipmentFexFsmRmtErrDescr OBJECT-TYPE
    SYNTAX       SnmpAdminString
    MAX-ACCESS   read-only
    STATUS       current
    DESCRIPTION
        "Cisco Firepower equipment:FexFsm:rmtErrDescr managed
        object property"
    ::= { cfprEquipmentFexFsmEntry 10 }

cfprEquipmentFexFsmRmtRslt OBJECT-TYPE
    SYNTAX       CfprConditionRemoteInvRslt
    MAX-ACCESS   read-only
    STATUS       current
    DESCRIPTION
        "Cisco Firepower equipment:FexFsm:rmtRslt managed object property"
    ::= { cfprEquipmentFexFsmEntry 11 }

cfprEquipmentFexFsmStageTable OBJECT-TYPE
    SYNTAX           SEQUENCE OF CfprEquipmentFexFsmStageEntry
    MAX-ACCESS       not-accessible
    STATUS           current
    DESCRIPTION
        "Cisco Firepower equipment:FexFsmStage managed object table"
    ::= { cfprEquipmentObjects 47 }

cfprEquipmentFexFsmStageEntry OBJECT-TYPE
    SYNTAX           CfprEquipmentFexFsmStageEntry
    MAX-ACCESS       not-accessible
    STATUS           current
    DESCRIPTION
        "Entry for the cfprEquipmentFexFsmStageTable table."
    INDEX { cfprEquipmentFexFsmStageInstanceId }
    ::= { cfprEquipmentFexFsmStageTable 1 }

CfprEquipmentFexFsmStageEntry ::= SEQUENCE {
    cfprEquipmentFexFsmStageInstanceId                               CfprManagedObjectId,
    cfprEquipmentFexFsmStageDn                                       CfprManagedObjectDn,
    cfprEquipmentFexFsmStageRn                                       SnmpAdminString,
    cfprEquipmentFexFsmStageDescrData                                SnmpAdminString,
    cfprEquipmentFexFsmStageLastUpdateTime                           DateAndTime,
    cfprEquipmentFexFsmStageName                                     CfprEquipmentFexFsmStageName,
    cfprEquipmentFexFsmStageOrder                                    Gauge32,
    cfprEquipmentFexFsmStageRetry                                    Gauge32,
    cfprEquipmentFexFsmStageStageStatus                              CfprFsmFsmStageStatus
}

cfprEquipmentFexFsmStageInstanceId OBJECT-TYPE
    SYNTAX       CfprManagedObjectId
    MAX-ACCESS   not-accessible
    STATUS       current
    DESCRIPTION
        "Instance identifier of the managed object."
    ::= { cfprEquipmentFexFsmStageEntry 1 }

cfprEquipmentFexFsmStageDn OBJECT-TYPE
    SYNTAX       CfprManagedObjectDn
    MAX-ACCESS   read-only
    STATUS       current
    DESCRIPTION
        "Cisco Firepower equipment:FexFsmStage:dn managed object property"
    ::= { cfprEquipmentFexFsmStageEntry 2 }

cfprEquipmentFexFsmStageRn OBJECT-TYPE
    SYNTAX       SnmpAdminString
    MAX-ACCESS   read-only
    STATUS       current
    DESCRIPTION
        "Cisco Firepower equipment:FexFsmStage:rn managed object property"
    ::= { cfprEquipmentFexFsmStageEntry 3 }

cfprEquipmentFexFsmStageDescrData OBJECT-TYPE
    SYNTAX       SnmpAdminString
    MAX-ACCESS   read-only
    STATUS       current
    DESCRIPTION
        "Cisco Firepower equipment:FexFsmStage:descr managed
        object property"
    ::= { cfprEquipmentFexFsmStageEntry 4 }

cfprEquipmentFexFsmStageLastUpdateTime OBJECT-TYPE
    SYNTAX       DateAndTime
    MAX-ACCESS   read-only
    STATUS       current
    DESCRIPTION
        "Cisco Firepower equipment:FexFsmStage:lastUpdateTime
        managed object property"
    ::= { cfprEquipmentFexFsmStageEntry 5 }

cfprEquipmentFexFsmStageName OBJECT-TYPE
    SYNTAX       CfprEquipmentFexFsmStageName
    MAX-ACCESS   read-only
    STATUS       current
    DESCRIPTION
        "Cisco Firepower equipment:FexFsmStage:name managed
        object property"
    ::= { cfprEquipmentFexFsmStageEntry 6 }

cfprEquipmentFexFsmStageOrder OBJECT-TYPE
    SYNTAX       Gauge32
    MAX-ACCESS   read-only
    STATUS       current
    DESCRIPTION
        "Cisco Firepower equipment:FexFsmStage:order managed
        object property"
    ::= { cfprEquipmentFexFsmStageEntry 7 }

cfprEquipmentFexFsmStageRetry OBJECT-TYPE
    SYNTAX       Gauge32
    MAX-ACCESS   read-only
    STATUS       current
    DESCRIPTION
        "Cisco Firepower equipment:FexFsmStage:retry managed
        object property"
    ::= { cfprEquipmentFexFsmStageEntry 8 }

cfprEquipmentFexFsmStageStageStatus OBJECT-TYPE
    SYNTAX       CfprFsmFsmStageStatus
    MAX-ACCESS   read-only
    STATUS       current
    DESCRIPTION
        "Cisco Firepower equipment:FexFsmStage:stageStatus
        managed object property"
    ::= { cfprEquipmentFexFsmStageEntry 9 }

cfprEquipmentFexFsmTaskTable OBJECT-TYPE
    SYNTAX           SEQUENCE OF CfprEquipmentFexFsmTaskEntry
    MAX-ACCESS       not-accessible
    STATUS           current
    DESCRIPTION
        "Cisco Firepower equipment:FexFsmTask managed object table"
    ::= { cfprEquipmentObjects 48 }

cfprEquipmentFexFsmTaskEntry OBJECT-TYPE
    SYNTAX           CfprEquipmentFexFsmTaskEntry
    MAX-ACCESS       not-accessible
    STATUS           current
    DESCRIPTION
        "Entry for the cfprEquipmentFexFsmTaskTable table."
    INDEX { cfprEquipmentFexFsmTaskInstanceId }
    ::= { cfprEquipmentFexFsmTaskTable 1 }

CfprEquipmentFexFsmTaskEntry ::= SEQUENCE {
    cfprEquipmentFexFsmTaskInstanceId                                CfprManagedObjectId,
    cfprEquipmentFexFsmTaskDn                                        CfprManagedObjectDn,
    cfprEquipmentFexFsmTaskRn                                        SnmpAdminString,
    cfprEquipmentFexFsmTaskCompletion                                CfprFsmCompletion,
    cfprEquipmentFexFsmTaskFlags                                     CfprFsmFlags,
    cfprEquipmentFexFsmTaskItem                                      CfprEquipmentFexFsmTaskItem,
    cfprEquipmentFexFsmTaskSeqId                                     Gauge32
}

cfprEquipmentFexFsmTaskInstanceId OBJECT-TYPE
    SYNTAX       CfprManagedObjectId
    MAX-ACCESS   not-accessible
    STATUS       current
    DESCRIPTION
        "Instance identifier of the managed object."
    ::= { cfprEquipmentFexFsmTaskEntry 1 }

cfprEquipmentFexFsmTaskDn OBJECT-TYPE
    SYNTAX       CfprManagedObjectDn
    MAX-ACCESS   read-only
    STATUS       current
    DESCRIPTION
        "Cisco Firepower equipment:FexFsmTask:dn managed object property"
    ::= { cfprEquipmentFexFsmTaskEntry 2 }

cfprEquipmentFexFsmTaskRn OBJECT-TYPE
    SYNTAX       SnmpAdminString
    MAX-ACCESS   read-only
    STATUS       current
    DESCRIPTION
        "Cisco Firepower equipment:FexFsmTask:rn managed object property"
    ::= { cfprEquipmentFexFsmTaskEntry 3 }

cfprEquipmentFexFsmTaskCompletion OBJECT-TYPE
    SYNTAX       CfprFsmCompletion
    MAX-ACCESS   read-only
    STATUS       current
    DESCRIPTION
        "Cisco Firepower equipment:FexFsmTask:completion
        managed object property"
    ::= { cfprEquipmentFexFsmTaskEntry 4 }

cfprEquipmentFexFsmTaskFlags OBJECT-TYPE
    SYNTAX       CfprFsmFlags
    MAX-ACCESS   read-only
    STATUS       current
    DESCRIPTION
        "Cisco Firepower equipment:FexFsmTask:flags managed
        object property"
    ::= { cfprEquipmentFexFsmTaskEntry 5 }

cfprEquipmentFexFsmTaskItem OBJECT-TYPE
    SYNTAX       CfprEquipmentFexFsmTaskItem
    MAX-ACCESS   read-only
    STATUS       current
    DESCRIPTION
        "Cisco Firepower equipment:FexFsmTask:item managed
        object property"
    ::= { cfprEquipmentFexFsmTaskEntry 6 }

cfprEquipmentFexFsmTaskSeqId OBJECT-TYPE
    SYNTAX       Gauge32
    MAX-ACCESS   read-only
    STATUS       current
    DESCRIPTION
        "Cisco Firepower equipment:FexFsmTask:seqId managed
        object property"
    ::= { cfprEquipmentFexFsmTaskEntry 7 }

cfprEquipmentFexPowerSummaryTable OBJECT-TYPE
    SYNTAX           SEQUENCE OF CfprEquipmentFexPowerSummaryEntry
    MAX-ACCESS       not-accessible
    STATUS           current
    DESCRIPTION
        "Cisco Firepower equipment:FexPowerSummary managed object table"
    ::= { cfprEquipmentObjects 49 }

cfprEquipmentFexPowerSummaryEntry OBJECT-TYPE
    SYNTAX           CfprEquipmentFexPowerSummaryEntry
    MAX-ACCESS       not-accessible
    STATUS           current
    DESCRIPTION
        "Entry for the cfprEquipmentFexPowerSummaryTable table."
    INDEX { cfprEquipmentFexPowerSummaryInstanceId }
    ::= { cfprEquipmentFexPowerSummaryTable 1 }

CfprEquipmentFexPowerSummaryEntry ::= SEQUENCE {
    cfprEquipmentFexPowerSummaryInstanceId                           CfprManagedObjectId,
    cfprEquipmentFexPowerSummaryDn                                   CfprManagedObjectDn,
    cfprEquipmentFexPowerSummaryRn                                   SnmpAdminString,
    cfprEquipmentFexPowerSummaryModulePower                          INTEGER,
    cfprEquipmentFexPowerSummaryModulePowerAvg                       INTEGER,
    cfprEquipmentFexPowerSummaryModulePowerMax                       INTEGER,
    cfprEquipmentFexPowerSummaryModulePowerMin                       INTEGER,
    cfprEquipmentFexPowerSummaryAvailablePower                       INTEGER,
    cfprEquipmentFexPowerSummaryAvailablePowerAvg                    INTEGER,
    cfprEquipmentFexPowerSummaryAvailablePowerMax                    INTEGER,
    cfprEquipmentFexPowerSummaryAvailablePowerMin                    INTEGER,
    cfprEquipmentFexPowerSummaryIntervals                            Gauge32,
    cfprEquipmentFexPowerSummaryReservedPower                        INTEGER,
    cfprEquipmentFexPowerSummaryReservedPowerAvg                     INTEGER,
    cfprEquipmentFexPowerSummaryReservedPowerMax                     INTEGER,
    cfprEquipmentFexPowerSummaryReservedPowerMin                     INTEGER,
    cfprEquipmentFexPowerSummarySuspect                              TruthValue,
    cfprEquipmentFexPowerSummaryThresholded                          CfprEquipmentFexPowerSummaryThresholded,
    cfprEquipmentFexPowerSummaryTimeCollected                        DateAndTime,
    cfprEquipmentFexPowerSummaryTotalPower                           INTEGER,
    cfprEquipmentFexPowerSummaryTotalPowerAvg                        INTEGER,
    cfprEquipmentFexPowerSummaryTotalPowerMax                        INTEGER,
    cfprEquipmentFexPowerSummaryTotalPowerMin                        INTEGER,
    cfprEquipmentFexPowerSummaryUpdate                               Gauge32
}

cfprEquipmentFexPowerSummaryInstanceId OBJECT-TYPE
    SYNTAX       CfprManagedObjectId
    MAX-ACCESS   not-accessible
    STATUS       current
    DESCRIPTION
        "Instance identifier of the managed object."
    ::= { cfprEquipmentFexPowerSummaryEntry 1 }

cfprEquipmentFexPowerSummaryDn OBJECT-TYPE
    SYNTAX       CfprManagedObjectDn
    MAX-ACCESS   read-only
    STATUS       current
    DESCRIPTION
        "Cisco Firepower equipment:FexPowerSummary:dn managed
        object property"
    ::= { cfprEquipmentFexPowerSummaryEntry 2 }

cfprEquipmentFexPowerSummaryRn OBJECT-TYPE
    SYNTAX       SnmpAdminString
    MAX-ACCESS   read-only
    STATUS       current
    DESCRIPTION
        "Cisco Firepower equipment:FexPowerSummary:rn managed
        object property"
    ::= { cfprEquipmentFexPowerSummaryEntry 3 }

cfprEquipmentFexPowerSummaryModulePower OBJECT-TYPE
    SYNTAX       INTEGER
    MAX-ACCESS   read-only
    STATUS       current
    DESCRIPTION
        "Cisco Firepower equipment:FexPowerSummary:ModulePower
        managed object property"
    ::= { cfprEquipmentFexPowerSummaryEntry 4 }

cfprEquipmentFexPowerSummaryModulePowerAvg OBJECT-TYPE
    SYNTAX       INTEGER
    MAX-ACCESS   read-only
    STATUS       current
    DESCRIPTION
        "Cisco Firepower equipment:FexPowerSummary:ModulePowerAvg
        managed object property"
    ::= { cfprEquipmentFexPowerSummaryEntry 5 }

cfprEquipmentFexPowerSummaryModulePowerMax OBJECT-TYPE
    SYNTAX       INTEGER
    MAX-ACCESS   read-only
    STATUS       current
    DESCRIPTION
        "Cisco Firepower equipment:FexPowerSummary:ModulePowerMax
        managed object property"
    ::= { cfprEquipmentFexPowerSummaryEntry 6 }

cfprEquipmentFexPowerSummaryModulePowerMin OBJECT-TYPE
    SYNTAX       INTEGER
    MAX-ACCESS   read-only
    STATUS       current
    DESCRIPTION
        "Cisco Firepower equipment:FexPowerSummary:ModulePowerMin
        managed object property"
    ::= { cfprEquipmentFexPowerSummaryEntry 7 }

cfprEquipmentFexPowerSummaryAvailablePower OBJECT-TYPE
    SYNTAX       INTEGER
    MAX-ACCESS   read-only
    STATUS       current
    DESCRIPTION
        "Cisco Firepower equipment:FexPowerSummary:availablePower
        managed object property"
    ::= { cfprEquipmentFexPowerSummaryEntry 8 }

cfprEquipmentFexPowerSummaryAvailablePowerAvg OBJECT-TYPE
    SYNTAX       INTEGER
    MAX-ACCESS   read-only
    STATUS       current
    DESCRIPTION
        "Cisco Firepower equipment:FexPowerSummary:availablePowerAvg
        managed object property"
    ::= { cfprEquipmentFexPowerSummaryEntry 9 }

cfprEquipmentFexPowerSummaryAvailablePowerMax OBJECT-TYPE
    SYNTAX       INTEGER
    MAX-ACCESS   read-only
    STATUS       current
    DESCRIPTION
        "Cisco Firepower equipment:FexPowerSummary:availablePowerMax
        managed object property"
    ::= { cfprEquipmentFexPowerSummaryEntry 10 }

cfprEquipmentFexPowerSummaryAvailablePowerMin OBJECT-TYPE
    SYNTAX       INTEGER
    MAX-ACCESS   read-only
    STATUS       current
    DESCRIPTION
        "Cisco Firepower equipment:FexPowerSummary:availablePowerMin
        managed object property"
    ::= { cfprEquipmentFexPowerSummaryEntry 11 }

cfprEquipmentFexPowerSummaryIntervals OBJECT-TYPE
    SYNTAX       Gauge32
    MAX-ACCESS   read-only
    STATUS       current
    DESCRIPTION
        "Cisco Firepower equipment:FexPowerSummary:intervals
        managed object property"
    ::= { cfprEquipmentFexPowerSummaryEntry 12 }

cfprEquipmentFexPowerSummaryReservedPower OBJECT-TYPE
    SYNTAX       INTEGER
    MAX-ACCESS   read-only
    STATUS       current
    DESCRIPTION
        "Cisco Firepower equipment:FexPowerSummary:reservedPower
        managed object property"
    ::= { cfprEquipmentFexPowerSummaryEntry 13 }

cfprEquipmentFexPowerSummaryReservedPowerAvg OBJECT-TYPE
    SYNTAX       INTEGER
    MAX-ACCESS   read-only
    STATUS       current
    DESCRIPTION
        "Cisco Firepower equipment:FexPowerSummary:reservedPowerAvg
        managed object property"
    ::= { cfprEquipmentFexPowerSummaryEntry 14 }

cfprEquipmentFexPowerSummaryReservedPowerMax OBJECT-TYPE
    SYNTAX       INTEGER
    MAX-ACCESS   read-only
    STATUS       current
    DESCRIPTION
        "Cisco Firepower equipment:FexPowerSummary:reservedPowerMax
        managed object property"
    ::= { cfprEquipmentFexPowerSummaryEntry 15 }

cfprEquipmentFexPowerSummaryReservedPowerMin OBJECT-TYPE
    SYNTAX       INTEGER
    MAX-ACCESS   read-only
    STATUS       current
    DESCRIPTION
        "Cisco Firepower equipment:FexPowerSummary:reservedPowerMin
        managed object property"
    ::= { cfprEquipmentFexPowerSummaryEntry 16 }

cfprEquipmentFexPowerSummarySuspect OBJECT-TYPE
    SYNTAX       TruthValue
    MAX-ACCESS   read-only
    STATUS       current
    DESCRIPTION
        "Cisco Firepower equipment:FexPowerSummary:suspect
        managed object property"
    ::= { cfprEquipmentFexPowerSummaryEntry 17 }

cfprEquipmentFexPowerSummaryThresholded OBJECT-TYPE
    SYNTAX       CfprEquipmentFexPowerSummaryThresholded
    MAX-ACCESS   read-only
    STATUS       current
    DESCRIPTION
        "Cisco Firepower equipment:FexPowerSummary:thresholded
        managed object property"
    ::= { cfprEquipmentFexPowerSummaryEntry 18 }

cfprEquipmentFexPowerSummaryTimeCollected OBJECT-TYPE
    SYNTAX       DateAndTime
    MAX-ACCESS   read-only
    STATUS       current
    DESCRIPTION
        "Cisco Firepower equipment:FexPowerSummary:timeCollected
        managed object property"
    ::= { cfprEquipmentFexPowerSummaryEntry 19 }

cfprEquipmentFexPowerSummaryTotalPower OBJECT-TYPE
    SYNTAX       INTEGER
    MAX-ACCESS   read-only
    STATUS       current
    DESCRIPTION
        "Cisco Firepower equipment:FexPowerSummary:totalPower
        managed object property"
    ::= { cfprEquipmentFexPowerSummaryEntry 20 }

cfprEquipmentFexPowerSummaryTotalPowerAvg OBJECT-TYPE
    SYNTAX       INTEGER
    MAX-ACCESS   read-only
    STATUS       current
    DESCRIPTION
        "Cisco Firepower equipment:FexPowerSummary:totalPowerAvg
        managed object property"
    ::= { cfprEquipmentFexPowerSummaryEntry 21 }

cfprEquipmentFexPowerSummaryTotalPowerMax OBJECT-TYPE
    SYNTAX       INTEGER
    MAX-ACCESS   read-only
    STATUS       current
    DESCRIPTION
        "Cisco Firepower equipment:FexPowerSummary:totalPowerMax
        managed object property"
    ::= { cfprEquipmentFexPowerSummaryEntry 22 }

cfprEquipmentFexPowerSummaryTotalPowerMin OBJECT-TYPE
    SYNTAX       INTEGER
    MAX-ACCESS   read-only
    STATUS       current
    DESCRIPTION
        "Cisco Firepower equipment:FexPowerSummary:totalPowerMin
        managed object property"
    ::= { cfprEquipmentFexPowerSummaryEntry 23 }

cfprEquipmentFexPowerSummaryUpdate OBJECT-TYPE
    SYNTAX       Gauge32
    MAX-ACCESS   read-only
    STATUS       current
    DESCRIPTION
        "Cisco Firepower equipment:FexPowerSummary:update
        managed object property"
    ::= { cfprEquipmentFexPowerSummaryEntry 24 }

cfprEquipmentFexPowerSummaryHistTable OBJECT-TYPE
    SYNTAX           SEQUENCE OF CfprEquipmentFexPowerSummaryHistEntry
    MAX-ACCESS       not-accessible
    STATUS           current
    DESCRIPTION
        "Cisco Firepower equipment:FexPowerSummaryHist
        managed object table"
    ::= { cfprEquipmentObjects 50 }

cfprEquipmentFexPowerSummaryHistEntry OBJECT-TYPE
    SYNTAX           CfprEquipmentFexPowerSummaryHistEntry
    MAX-ACCESS       not-accessible
    STATUS           current
    DESCRIPTION
        "Entry for the cfprEquipmentFexPowerSummaryHistTable table."
    INDEX { cfprEquipmentFexPowerSummaryHistInstanceId }
    ::= { cfprEquipmentFexPowerSummaryHistTable 1 }

CfprEquipmentFexPowerSummaryHistEntry ::= SEQUENCE {
    cfprEquipmentFexPowerSummaryHistInstanceId                       CfprManagedObjectId,
    cfprEquipmentFexPowerSummaryHistDn                               CfprManagedObjectDn,
    cfprEquipmentFexPowerSummaryHistRn                               SnmpAdminString,
    cfprEquipmentFexPowerSummaryHistModulePower                      INTEGER,
    cfprEquipmentFexPowerSummaryHistModulePowerAvg                   INTEGER,
    cfprEquipmentFexPowerSummaryHistModulePowerMax                   INTEGER,
    cfprEquipmentFexPowerSummaryHistModulePowerMin                   INTEGER,
    cfprEquipmentFexPowerSummaryHistAvailablePower                   INTEGER,
    cfprEquipmentFexPowerSummaryHistAvailablePowerAvg                INTEGER,
    cfprEquipmentFexPowerSummaryHistAvailablePowerMax                INTEGER,
    cfprEquipmentFexPowerSummaryHistAvailablePowerMin                INTEGER,
    cfprEquipmentFexPowerSummaryHistId                               Unsigned64,
    cfprEquipmentFexPowerSummaryHistMostRecent                       TruthValue,
    cfprEquipmentFexPowerSummaryHistReservedPower                    INTEGER,
    cfprEquipmentFexPowerSummaryHistReservedPowerAvg                 INTEGER,
    cfprEquipmentFexPowerSummaryHistReservedPowerMax                 INTEGER,
    cfprEquipmentFexPowerSummaryHistReservedPowerMin                 INTEGER,
    cfprEquipmentFexPowerSummaryHistSuspect                          TruthValue,
    cfprEquipmentFexPowerSummaryHistThresholded                      CfprEquipmentFexPowerSummaryHistThresholded,
    cfprEquipmentFexPowerSummaryHistTimeCollected                    DateAndTime,
    cfprEquipmentFexPowerSummaryHistTotalPower                       INTEGER,
    cfprEquipmentFexPowerSummaryHistTotalPowerAvg                    INTEGER,
    cfprEquipmentFexPowerSummaryHistTotalPowerMax                    INTEGER,
    cfprEquipmentFexPowerSummaryHistTotalPowerMin                    INTEGER
}

cfprEquipmentFexPowerSummaryHistInstanceId OBJECT-TYPE
    SYNTAX       CfprManagedObjectId
    MAX-ACCESS   not-accessible
    STATUS       current
    DESCRIPTION
        "Instance identifier of the managed object."
    ::= { cfprEquipmentFexPowerSummaryHistEntry 1 }

cfprEquipmentFexPowerSummaryHistDn OBJECT-TYPE
    SYNTAX       CfprManagedObjectDn
    MAX-ACCESS   read-only
    STATUS       current
    DESCRIPTION
        "Cisco Firepower equipment:FexPowerSummaryHist:dn
        managed object property"
    ::= { cfprEquipmentFexPowerSummaryHistEntry 2 }

cfprEquipmentFexPowerSummaryHistRn OBJECT-TYPE
    SYNTAX       SnmpAdminString
    MAX-ACCESS   read-only
    STATUS       current
    DESCRIPTION
        "Cisco Firepower equipment:FexPowerSummaryHist:rn
        managed object property"
    ::= { cfprEquipmentFexPowerSummaryHistEntry 3 }

cfprEquipmentFexPowerSummaryHistModulePower OBJECT-TYPE
    SYNTAX       INTEGER
    MAX-ACCESS   read-only
    STATUS       current
    DESCRIPTION
        "Cisco Firepower equipment:FexPowerSummaryHist:ModulePower
        managed object property"
    ::= { cfprEquipmentFexPowerSummaryHistEntry 4 }

cfprEquipmentFexPowerSummaryHistModulePowerAvg OBJECT-TYPE
    SYNTAX       INTEGER
    MAX-ACCESS   read-only
    STATUS       current
    DESCRIPTION
        "Cisco Firepower equipment:FexPowerSummaryHist:ModulePowerAvg
        managed object property"
    ::= { cfprEquipmentFexPowerSummaryHistEntry 5 }

cfprEquipmentFexPowerSummaryHistModulePowerMax OBJECT-TYPE
    SYNTAX       INTEGER
    MAX-ACCESS   read-only
    STATUS       current
    DESCRIPTION
        "Cisco Firepower equipment:FexPowerSummaryHist:ModulePowerMax
        managed object property"
    ::= { cfprEquipmentFexPowerSummaryHistEntry 6 }

cfprEquipmentFexPowerSummaryHistModulePowerMin OBJECT-TYPE
    SYNTAX       INTEGER
    MAX-ACCESS   read-only
    STATUS       current
    DESCRIPTION
        "Cisco Firepower equipment:FexPowerSummaryHist:ModulePowerMin
        managed object property"
    ::= { cfprEquipmentFexPowerSummaryHistEntry 7 }

cfprEquipmentFexPowerSummaryHistAvailablePower OBJECT-TYPE
    SYNTAX       INTEGER
    MAX-ACCESS   read-only
    STATUS       current
    DESCRIPTION
        "Cisco Firepower equipment:FexPowerSummaryHist:availablePower
        managed object property"
    ::= { cfprEquipmentFexPowerSummaryHistEntry 8 }

cfprEquipmentFexPowerSummaryHistAvailablePowerAvg OBJECT-TYPE
    SYNTAX       INTEGER
    MAX-ACCESS   read-only
    STATUS       current
    DESCRIPTION
        "Cisco Firepower equipment:FexPowerSummaryHist:availablePowerAvg
        managed object property"
    ::= { cfprEquipmentFexPowerSummaryHistEntry 9 }

cfprEquipmentFexPowerSummaryHistAvailablePowerMax OBJECT-TYPE
    SYNTAX       INTEGER
    MAX-ACCESS   read-only
    STATUS       current
    DESCRIPTION
        "Cisco Firepower equipment:FexPowerSummaryHist:availablePowerMax
        managed object property"
    ::= { cfprEquipmentFexPowerSummaryHistEntry 10 }

cfprEquipmentFexPowerSummaryHistAvailablePowerMin OBJECT-TYPE
    SYNTAX       INTEGER
    MAX-ACCESS   read-only
    STATUS       current
    DESCRIPTION
        "Cisco Firepower equipment:FexPowerSummaryHist:availablePowerMin
        managed object property"
    ::= { cfprEquipmentFexPowerSummaryHistEntry 11 }

cfprEquipmentFexPowerSummaryHistId OBJECT-TYPE
    SYNTAX       Unsigned64
    MAX-ACCESS   read-only
    STATUS       current
    DESCRIPTION
        "Cisco Firepower equipment:FexPowerSummaryHist:id
        managed object property"
    ::= { cfprEquipmentFexPowerSummaryHistEntry 12 }

cfprEquipmentFexPowerSummaryHistMostRecent OBJECT-TYPE
    SYNTAX       TruthValue
    MAX-ACCESS   read-only
    STATUS       current
    DESCRIPTION
        "Cisco Firepower equipment:FexPowerSummaryHist:mostRecent
        managed object property"
    ::= { cfprEquipmentFexPowerSummaryHistEntry 13 }

cfprEquipmentFexPowerSummaryHistReservedPower OBJECT-TYPE
    SYNTAX       INTEGER
    MAX-ACCESS   read-only
    STATUS       current
    DESCRIPTION
        "Cisco Firepower equipment:FexPowerSummaryHist:reservedPower
        managed object property"
    ::= { cfprEquipmentFexPowerSummaryHistEntry 14 }

cfprEquipmentFexPowerSummaryHistReservedPowerAvg OBJECT-TYPE
    SYNTAX       INTEGER
    MAX-ACCESS   read-only
    STATUS       current
    DESCRIPTION
        "Cisco Firepower equipment:FexPowerSummaryHist:reservedPowerAvg
        managed object property"
    ::= { cfprEquipmentFexPowerSummaryHistEntry 15 }

cfprEquipmentFexPowerSummaryHistReservedPowerMax OBJECT-TYPE
    SYNTAX       INTEGER
    MAX-ACCESS   read-only
    STATUS       current
    DESCRIPTION
        "Cisco Firepower equipment:FexPowerSummaryHist:reservedPowerMax
        managed object property"
    ::= { cfprEquipmentFexPowerSummaryHistEntry 16 }

cfprEquipmentFexPowerSummaryHistReservedPowerMin OBJECT-TYPE
    SYNTAX       INTEGER
    MAX-ACCESS   read-only
    STATUS       current
    DESCRIPTION
        "Cisco Firepower equipment:FexPowerSummaryHist:reservedPowerMin
        managed object property"
    ::= { cfprEquipmentFexPowerSummaryHistEntry 17 }

cfprEquipmentFexPowerSummaryHistSuspect OBJECT-TYPE
    SYNTAX       TruthValue
    MAX-ACCESS   read-only
    STATUS       current
    DESCRIPTION
        "Cisco Firepower equipment:FexPowerSummaryHist:suspect
        managed object property"
    ::= { cfprEquipmentFexPowerSummaryHistEntry 18 }

cfprEquipmentFexPowerSummaryHistThresholded OBJECT-TYPE
    SYNTAX       CfprEquipmentFexPowerSummaryHistThresholded
    MAX-ACCESS   read-only
    STATUS       current
    DESCRIPTION
        "Cisco Firepower equipment:FexPowerSummaryHist:thresholded
        managed object property"
    ::= { cfprEquipmentFexPowerSummaryHistEntry 19 }

cfprEquipmentFexPowerSummaryHistTimeCollected OBJECT-TYPE
    SYNTAX       DateAndTime
    MAX-ACCESS   read-only
    STATUS       current
    DESCRIPTION
        "Cisco Firepower equipment:FexPowerSummaryHist:timeCollected
        managed object property"
    ::= { cfprEquipmentFexPowerSummaryHistEntry 20 }

cfprEquipmentFexPowerSummaryHistTotalPower OBJECT-TYPE
    SYNTAX       INTEGER
    MAX-ACCESS   read-only
    STATUS       current
    DESCRIPTION
        "Cisco Firepower equipment:FexPowerSummaryHist:totalPower
        managed object property"
    ::= { cfprEquipmentFexPowerSummaryHistEntry 21 }

cfprEquipmentFexPowerSummaryHistTotalPowerAvg OBJECT-TYPE
    SYNTAX       INTEGER
    MAX-ACCESS   read-only
    STATUS       current
    DESCRIPTION
        "Cisco Firepower equipment:FexPowerSummaryHist:totalPowerAvg
        managed object property"
    ::= { cfprEquipmentFexPowerSummaryHistEntry 22 }

cfprEquipmentFexPowerSummaryHistTotalPowerMax OBJECT-TYPE
    SYNTAX       INTEGER
    MAX-ACCESS   read-only
    STATUS       current
    DESCRIPTION
        "Cisco Firepower equipment:FexPowerSummaryHist:totalPowerMax
        managed object property"
    ::= { cfprEquipmentFexPowerSummaryHistEntry 23 }

cfprEquipmentFexPowerSummaryHistTotalPowerMin OBJECT-TYPE
    SYNTAX       INTEGER
    MAX-ACCESS   read-only
    STATUS       current
    DESCRIPTION
        "Cisco Firepower equipment:FexPowerSummaryHist:totalPowerMin
        managed object property"
    ::= { cfprEquipmentFexPowerSummaryHistEntry 24 }

cfprEquipmentFexPsuInputStatsTable OBJECT-TYPE
    SYNTAX           SEQUENCE OF CfprEquipmentFexPsuInputStatsEntry
    MAX-ACCESS       not-accessible
    STATUS           current
    DESCRIPTION
        "Cisco Firepower equipment:FexPsuInputStats managed object table"
    ::= { cfprEquipmentObjects 51 }

cfprEquipmentFexPsuInputStatsEntry OBJECT-TYPE
    SYNTAX           CfprEquipmentFexPsuInputStatsEntry
    MAX-ACCESS       not-accessible
    STATUS           current
    DESCRIPTION
        "Entry for the cfprEquipmentFexPsuInputStatsTable table."
    INDEX { cfprEquipmentFexPsuInputStatsInstanceId }
    ::= { cfprEquipmentFexPsuInputStatsTable 1 }

CfprEquipmentFexPsuInputStatsEntry ::= SEQUENCE {
    cfprEquipmentFexPsuInputStatsInstanceId                          CfprManagedObjectId,
    cfprEquipmentFexPsuInputStatsDn                                  CfprManagedObjectDn,
    cfprEquipmentFexPsuInputStatsRn                                  SnmpAdminString,
    cfprEquipmentFexPsuInputStatsCurrent                             INTEGER,
    cfprEquipmentFexPsuInputStatsCurrentAvg                          INTEGER,
    cfprEquipmentFexPsuInputStatsCurrentMax                          INTEGER,
    cfprEquipmentFexPsuInputStatsCurrentMin                          INTEGER,
    cfprEquipmentFexPsuInputStatsInputStatus                         SnmpAdminString,
    cfprEquipmentFexPsuInputStatsIntervals                           Gauge32,
    cfprEquipmentFexPsuInputStatsPower                               INTEGER,
    cfprEquipmentFexPsuInputStatsPowerAvg                            INTEGER,
    cfprEquipmentFexPsuInputStatsPowerMax                            INTEGER,
    cfprEquipmentFexPsuInputStatsPowerMin                            INTEGER,
    cfprEquipmentFexPsuInputStatsSuspect                             TruthValue,
    cfprEquipmentFexPsuInputStatsThresholded                         CfprEquipmentFexPsuInputStatsThresholded,
    cfprEquipmentFexPsuInputStatsTimeCollected                       DateAndTime,
    cfprEquipmentFexPsuInputStatsUpdate                              Gauge32,
    cfprEquipmentFexPsuInputStatsVoltage                             INTEGER,
    cfprEquipmentFexPsuInputStatsVoltageAvg                          INTEGER,
    cfprEquipmentFexPsuInputStatsVoltageMax                          INTEGER,
    cfprEquipmentFexPsuInputStatsVoltageMin                          INTEGER
}

cfprEquipmentFexPsuInputStatsInstanceId OBJECT-TYPE
    SYNTAX       CfprManagedObjectId
    MAX-ACCESS   not-accessible
    STATUS       current
    DESCRIPTION
        "Instance identifier of the managed object."
    ::= { cfprEquipmentFexPsuInputStatsEntry 1 }

cfprEquipmentFexPsuInputStatsDn OBJECT-TYPE
    SYNTAX       CfprManagedObjectDn
    MAX-ACCESS   read-only
    STATUS       current
    DESCRIPTION
        "Cisco Firepower equipment:FexPsuInputStats:dn
        managed object property"
    ::= { cfprEquipmentFexPsuInputStatsEntry 2 }

cfprEquipmentFexPsuInputStatsRn OBJECT-TYPE
    SYNTAX       SnmpAdminString
    MAX-ACCESS   read-only
    STATUS       current
    DESCRIPTION
        "Cisco Firepower equipment:FexPsuInputStats:rn
        managed object property"
    ::= { cfprEquipmentFexPsuInputStatsEntry 3 }

cfprEquipmentFexPsuInputStatsCurrent OBJECT-TYPE
    SYNTAX       INTEGER
    MAX-ACCESS   read-only
    STATUS       current
    DESCRIPTION
        "Cisco Firepower equipment:FexPsuInputStats:current
        managed object property"
    ::= { cfprEquipmentFexPsuInputStatsEntry 4 }

cfprEquipmentFexPsuInputStatsCurrentAvg OBJECT-TYPE
    SYNTAX       INTEGER
    MAX-ACCESS   read-only
    STATUS       current
    DESCRIPTION
        "Cisco Firepower equipment:FexPsuInputStats:currentAvg
        managed object property"
    ::= { cfprEquipmentFexPsuInputStatsEntry 5 }

cfprEquipmentFexPsuInputStatsCurrentMax OBJECT-TYPE
    SYNTAX       INTEGER
    MAX-ACCESS   read-only
    STATUS       current
    DESCRIPTION
        "Cisco Firepower equipment:FexPsuInputStats:currentMax
        managed object property"
    ::= { cfprEquipmentFexPsuInputStatsEntry 6 }

cfprEquipmentFexPsuInputStatsCurrentMin OBJECT-TYPE
    SYNTAX       INTEGER
    MAX-ACCESS   read-only
    STATUS       current
    DESCRIPTION
        "Cisco Firepower equipment:FexPsuInputStats:currentMin
        managed object property"
    ::= { cfprEquipmentFexPsuInputStatsEntry 7 }

cfprEquipmentFexPsuInputStatsInputStatus OBJECT-TYPE
    SYNTAX       SnmpAdminString
    MAX-ACCESS   read-only
    STATUS       current
    DESCRIPTION
        "Cisco Firepower equipment:FexPsuInputStats:inputStatus
        managed object property"
    ::= { cfprEquipmentFexPsuInputStatsEntry 8 }

cfprEquipmentFexPsuInputStatsIntervals OBJECT-TYPE
    SYNTAX       Gauge32
    MAX-ACCESS   read-only
    STATUS       current
    DESCRIPTION
        "Cisco Firepower equipment:FexPsuInputStats:intervals
        managed object property"
    ::= { cfprEquipmentFexPsuInputStatsEntry 9 }

cfprEquipmentFexPsuInputStatsPower OBJECT-TYPE
    SYNTAX       INTEGER
    MAX-ACCESS   read-only
    STATUS       current
    DESCRIPTION
        "Cisco Firepower equipment:FexPsuInputStats:power
        managed object property"
    ::= { cfprEquipmentFexPsuInputStatsEntry 10 }

cfprEquipmentFexPsuInputStatsPowerAvg OBJECT-TYPE
    SYNTAX       INTEGER
    MAX-ACCESS   read-only
    STATUS       current
    DESCRIPTION
        "Cisco Firepower equipment:FexPsuInputStats:powerAvg
        managed object property"
    ::= { cfprEquipmentFexPsuInputStatsEntry 11 }

cfprEquipmentFexPsuInputStatsPowerMax OBJECT-TYPE
    SYNTAX       INTEGER
    MAX-ACCESS   read-only
    STATUS       current
    DESCRIPTION
        "Cisco Firepower equipment:FexPsuInputStats:powerMax
        managed object property"
    ::= { cfprEquipmentFexPsuInputStatsEntry 12 }

cfprEquipmentFexPsuInputStatsPowerMin OBJECT-TYPE
    SYNTAX       INTEGER
    MAX-ACCESS   read-only
    STATUS       current
    DESCRIPTION
        "Cisco Firepower equipment:FexPsuInputStats:powerMin
        managed object property"
    ::= { cfprEquipmentFexPsuInputStatsEntry 13 }

cfprEquipmentFexPsuInputStatsSuspect OBJECT-TYPE
    SYNTAX       TruthValue
    MAX-ACCESS   read-only
    STATUS       current
    DESCRIPTION
        "Cisco Firepower equipment:FexPsuInputStats:suspect
        managed object property"
    ::= { cfprEquipmentFexPsuInputStatsEntry 14 }

cfprEquipmentFexPsuInputStatsThresholded OBJECT-TYPE
    SYNTAX       CfprEquipmentFexPsuInputStatsThresholded
    MAX-ACCESS   read-only
    STATUS       current
    DESCRIPTION
        "Cisco Firepower equipment:FexPsuInputStats:thresholded
        managed object property"
    ::= { cfprEquipmentFexPsuInputStatsEntry 15 }

cfprEquipmentFexPsuInputStatsTimeCollected OBJECT-TYPE
    SYNTAX       DateAndTime
    MAX-ACCESS   read-only
    STATUS       current
    DESCRIPTION
        "Cisco Firepower equipment:FexPsuInputStats:timeCollected
        managed object property"
    ::= { cfprEquipmentFexPsuInputStatsEntry 16 }

cfprEquipmentFexPsuInputStatsUpdate OBJECT-TYPE
    SYNTAX       Gauge32
    MAX-ACCESS   read-only
    STATUS       current
    DESCRIPTION
        "Cisco Firepower equipment:FexPsuInputStats:update
        managed object property"
    ::= { cfprEquipmentFexPsuInputStatsEntry 17 }

cfprEquipmentFexPsuInputStatsVoltage OBJECT-TYPE
    SYNTAX       INTEGER
    MAX-ACCESS   read-only
    STATUS       current
    DESCRIPTION
        "Cisco Firepower equipment:FexPsuInputStats:voltage
        managed object property"
    ::= { cfprEquipmentFexPsuInputStatsEntry 18 }

cfprEquipmentFexPsuInputStatsVoltageAvg OBJECT-TYPE
    SYNTAX       INTEGER
    MAX-ACCESS   read-only
    STATUS       current
    DESCRIPTION
        "Cisco Firepower equipment:FexPsuInputStats:voltageAvg
        managed object property"
    ::= { cfprEquipmentFexPsuInputStatsEntry 19 }

cfprEquipmentFexPsuInputStatsVoltageMax OBJECT-TYPE
    SYNTAX       INTEGER
    MAX-ACCESS   read-only
    STATUS       current
    DESCRIPTION
        "Cisco Firepower equipment:FexPsuInputStats:voltageMax
        managed object property"
    ::= { cfprEquipmentFexPsuInputStatsEntry 20 }

cfprEquipmentFexPsuInputStatsVoltageMin OBJECT-TYPE
    SYNTAX       INTEGER
    MAX-ACCESS   read-only
    STATUS       current
    DESCRIPTION
        "Cisco Firepower equipment:FexPsuInputStats:voltageMin
        managed object property"
    ::= { cfprEquipmentFexPsuInputStatsEntry 21 }

cfprEquipmentFexPsuInputStatsHistTable OBJECT-TYPE
    SYNTAX           SEQUENCE OF CfprEquipmentFexPsuInputStatsHistEntry
    MAX-ACCESS       not-accessible
    STATUS           current
    DESCRIPTION
        "Cisco Firepower equipment:FexPsuInputStatsHist
        managed object table"
    ::= { cfprEquipmentObjects 52 }

cfprEquipmentFexPsuInputStatsHistEntry OBJECT-TYPE
    SYNTAX           CfprEquipmentFexPsuInputStatsHistEntry
    MAX-ACCESS       not-accessible
    STATUS           current
    DESCRIPTION
        "Entry for the cfprEquipmentFexPsuInputStatsHistTable table."
    INDEX { cfprEquipmentFexPsuInputStatsHistInstanceId }
    ::= { cfprEquipmentFexPsuInputStatsHistTable 1 }

CfprEquipmentFexPsuInputStatsHistEntry ::= SEQUENCE {
    cfprEquipmentFexPsuInputStatsHistInstanceId                      CfprManagedObjectId,
    cfprEquipmentFexPsuInputStatsHistDn                              CfprManagedObjectDn,
    cfprEquipmentFexPsuInputStatsHistRn                              SnmpAdminString,
    cfprEquipmentFexPsuInputStatsHistCurrent                         INTEGER,
    cfprEquipmentFexPsuInputStatsHistCurrentAvg                      INTEGER,
    cfprEquipmentFexPsuInputStatsHistCurrentMax                      INTEGER,
    cfprEquipmentFexPsuInputStatsHistCurrentMin                      INTEGER,
    cfprEquipmentFexPsuInputStatsHistId                              Unsigned64,
    cfprEquipmentFexPsuInputStatsHistMostRecent                      TruthValue,
    cfprEquipmentFexPsuInputStatsHistPower                           INTEGER,
    cfprEquipmentFexPsuInputStatsHistPowerAvg                        INTEGER,
    cfprEquipmentFexPsuInputStatsHistPowerMax                        INTEGER,
    cfprEquipmentFexPsuInputStatsHistPowerMin                        INTEGER,
    cfprEquipmentFexPsuInputStatsHistSuspect                         TruthValue,
    cfprEquipmentFexPsuInputStatsHistThresholded                     CfprEquipmentFexPsuInputStatsHistThresholded,
    cfprEquipmentFexPsuInputStatsHistTimeCollected                   DateAndTime,
    cfprEquipmentFexPsuInputStatsHistVoltage                         INTEGER,
    cfprEquipmentFexPsuInputStatsHistVoltageAvg                      INTEGER,
    cfprEquipmentFexPsuInputStatsHistVoltageMax                      INTEGER,
    cfprEquipmentFexPsuInputStatsHistVoltageMin                      INTEGER
}

cfprEquipmentFexPsuInputStatsHistInstanceId OBJECT-TYPE
    SYNTAX       CfprManagedObjectId
    MAX-ACCESS   not-accessible
    STATUS       current
    DESCRIPTION
        "Instance identifier of the managed object."
    ::= { cfprEquipmentFexPsuInputStatsHistEntry 1 }

cfprEquipmentFexPsuInputStatsHistDn OBJECT-TYPE
    SYNTAX       CfprManagedObjectDn
    MAX-ACCESS   read-only
    STATUS       current
    DESCRIPTION
        "Cisco Firepower equipment:FexPsuInputStatsHist:dn
        managed object property"
    ::= { cfprEquipmentFexPsuInputStatsHistEntry 2 }

cfprEquipmentFexPsuInputStatsHistRn OBJECT-TYPE
    SYNTAX       SnmpAdminString
    MAX-ACCESS   read-only
    STATUS       current
    DESCRIPTION
        "Cisco Firepower equipment:FexPsuInputStatsHist:rn
        managed object property"
    ::= { cfprEquipmentFexPsuInputStatsHistEntry 3 }

cfprEquipmentFexPsuInputStatsHistCurrent OBJECT-TYPE
    SYNTAX       INTEGER
    MAX-ACCESS   read-only
    STATUS       current
    DESCRIPTION
        "Cisco Firepower equipment:FexPsuInputStatsHist:current
        managed object property"
    ::= { cfprEquipmentFexPsuInputStatsHistEntry 4 }

cfprEquipmentFexPsuInputStatsHistCurrentAvg OBJECT-TYPE
    SYNTAX       INTEGER
    MAX-ACCESS   read-only
    STATUS       current
    DESCRIPTION
        "Cisco Firepower equipment:FexPsuInputStatsHist:currentAvg
        managed object property"
    ::= { cfprEquipmentFexPsuInputStatsHistEntry 5 }

cfprEquipmentFexPsuInputStatsHistCurrentMax OBJECT-TYPE
    SYNTAX       INTEGER
    MAX-ACCESS   read-only
    STATUS       current
    DESCRIPTION
        "Cisco Firepower equipment:FexPsuInputStatsHist:currentMax
        managed object property"
    ::= { cfprEquipmentFexPsuInputStatsHistEntry 6 }

cfprEquipmentFexPsuInputStatsHistCurrentMin OBJECT-TYPE
    SYNTAX       INTEGER
    MAX-ACCESS   read-only
    STATUS       current
    DESCRIPTION
        "Cisco Firepower equipment:FexPsuInputStatsHist:currentMin
        managed object property"
    ::= { cfprEquipmentFexPsuInputStatsHistEntry 7 }

cfprEquipmentFexPsuInputStatsHistId OBJECT-TYPE
    SYNTAX       Unsigned64
    MAX-ACCESS   read-only
    STATUS       current
    DESCRIPTION
        "Cisco Firepower equipment:FexPsuInputStatsHist:id
        managed object property"
    ::= { cfprEquipmentFexPsuInputStatsHistEntry 8 }

cfprEquipmentFexPsuInputStatsHistMostRecent OBJECT-TYPE
    SYNTAX       TruthValue
    MAX-ACCESS   read-only
    STATUS       current
    DESCRIPTION
        "Cisco Firepower equipment:FexPsuInputStatsHist:mostRecent
        managed object property"
    ::= { cfprEquipmentFexPsuInputStatsHistEntry 9 }

cfprEquipmentFexPsuInputStatsHistPower OBJECT-TYPE
    SYNTAX       INTEGER
    MAX-ACCESS   read-only
    STATUS       current
    DESCRIPTION
        "Cisco Firepower equipment:FexPsuInputStatsHist:power
        managed object property"
    ::= { cfprEquipmentFexPsuInputStatsHistEntry 10 }

cfprEquipmentFexPsuInputStatsHistPowerAvg OBJECT-TYPE
    SYNTAX       INTEGER
    MAX-ACCESS   read-only
    STATUS       current
    DESCRIPTION
        "Cisco Firepower equipment:FexPsuInputStatsHist:powerAvg
        managed object property"
    ::= { cfprEquipmentFexPsuInputStatsHistEntry 11 }

cfprEquipmentFexPsuInputStatsHistPowerMax OBJECT-TYPE
    SYNTAX       INTEGER
    MAX-ACCESS   read-only
    STATUS       current
    DESCRIPTION
        "Cisco Firepower equipment:FexPsuInputStatsHist:powerMax
        managed object property"
    ::= { cfprEquipmentFexPsuInputStatsHistEntry 12 }

cfprEquipmentFexPsuInputStatsHistPowerMin OBJECT-TYPE
    SYNTAX       INTEGER
    MAX-ACCESS   read-only
    STATUS       current
    DESCRIPTION
        "Cisco Firepower equipment:FexPsuInputStatsHist:powerMin
        managed object property"
    ::= { cfprEquipmentFexPsuInputStatsHistEntry 13 }

cfprEquipmentFexPsuInputStatsHistSuspect OBJECT-TYPE
    SYNTAX       TruthValue
    MAX-ACCESS   read-only
    STATUS       current
    DESCRIPTION
        "Cisco Firepower equipment:FexPsuInputStatsHist:suspect
        managed object property"
    ::= { cfprEquipmentFexPsuInputStatsHistEntry 14 }

cfprEquipmentFexPsuInputStatsHistThresholded OBJECT-TYPE
    SYNTAX       CfprEquipmentFexPsuInputStatsHistThresholded
    MAX-ACCESS   read-only
    STATUS       current
    DESCRIPTION
        "Cisco Firepower equipment:FexPsuInputStatsHist:thresholded
        managed object property"
    ::= { cfprEquipmentFexPsuInputStatsHistEntry 15 }

cfprEquipmentFexPsuInputStatsHistTimeCollected OBJECT-TYPE
    SYNTAX       DateAndTime
    MAX-ACCESS   read-only
    STATUS       current
    DESCRIPTION
        "Cisco Firepower equipment:FexPsuInputStatsHist:timeCollected
        managed object property"
    ::= { cfprEquipmentFexPsuInputStatsHistEntry 16 }

cfprEquipmentFexPsuInputStatsHistVoltage OBJECT-TYPE
    SYNTAX       INTEGER
    MAX-ACCESS   read-only
    STATUS       current
    DESCRIPTION
        "Cisco Firepower equipment:FexPsuInputStatsHist:voltage
        managed object property"
    ::= { cfprEquipmentFexPsuInputStatsHistEntry 17 }

cfprEquipmentFexPsuInputStatsHistVoltageAvg OBJECT-TYPE
    SYNTAX       INTEGER
    MAX-ACCESS   read-only
    STATUS       current
    DESCRIPTION
        "Cisco Firepower equipment:FexPsuInputStatsHist:voltageAvg
        managed object property"
    ::= { cfprEquipmentFexPsuInputStatsHistEntry 18 }

cfprEquipmentFexPsuInputStatsHistVoltageMax OBJECT-TYPE
    SYNTAX       INTEGER
    MAX-ACCESS   read-only
    STATUS       current
    DESCRIPTION
        "Cisco Firepower equipment:FexPsuInputStatsHist:voltageMax
        managed object property"
    ::= { cfprEquipmentFexPsuInputStatsHistEntry 19 }

cfprEquipmentFexPsuInputStatsHistVoltageMin OBJECT-TYPE
    SYNTAX       INTEGER
    MAX-ACCESS   read-only
    STATUS       current
    DESCRIPTION
        "Cisco Firepower equipment:FexPsuInputStatsHist:voltageMin
        managed object property"
    ::= { cfprEquipmentFexPsuInputStatsHistEntry 20 }

cfprEquipmentFirmwareConstraintTable OBJECT-TYPE
    SYNTAX           SEQUENCE OF CfprEquipmentFirmwareConstraintEntry
    MAX-ACCESS       not-accessible
    STATUS           current
    DESCRIPTION
        "Cisco Firepower equipment:FirmwareConstraint managed
        object table"
    ::= { cfprEquipmentObjects 53 }

cfprEquipmentFirmwareConstraintEntry OBJECT-TYPE
    SYNTAX           CfprEquipmentFirmwareConstraintEntry
    MAX-ACCESS       not-accessible
    STATUS           current
    DESCRIPTION
        "Entry for the cfprEquipmentFirmwareConstraintTable table."
    INDEX { cfprEquipmentFirmwareConstraintInstanceId }
    ::= { cfprEquipmentFirmwareConstraintTable 1 }

CfprEquipmentFirmwareConstraintEntry ::= SEQUENCE {
    cfprEquipmentFirmwareConstraintInstanceId                        CfprManagedObjectId,
    cfprEquipmentFirmwareConstraintDn                                CfprManagedObjectDn,
    cfprEquipmentFirmwareConstraintRn                                SnmpAdminString,
    cfprEquipmentFirmwareConstraintMinVer1                           SnmpAdminString,
    cfprEquipmentFirmwareConstraintMinVer2                           SnmpAdminString
}

cfprEquipmentFirmwareConstraintInstanceId OBJECT-TYPE
    SYNTAX       CfprManagedObjectId
    MAX-ACCESS   not-accessible
    STATUS       current
    DESCRIPTION
        "Instance identifier of the managed object."
    ::= { cfprEquipmentFirmwareConstraintEntry 1 }

cfprEquipmentFirmwareConstraintDn OBJECT-TYPE
    SYNTAX       CfprManagedObjectDn
    MAX-ACCESS   read-only
    STATUS       current
    DESCRIPTION
        "Cisco Firepower equipment:FirmwareConstraint:dn
        managed object property"
    ::= { cfprEquipmentFirmwareConstraintEntry 2 }

cfprEquipmentFirmwareConstraintRn OBJECT-TYPE
    SYNTAX       SnmpAdminString
    MAX-ACCESS   read-only
    STATUS       current
    DESCRIPTION
        "Cisco Firepower equipment:FirmwareConstraint:rn
        managed object property"
    ::= { cfprEquipmentFirmwareConstraintEntry 3 }

cfprEquipmentFirmwareConstraintMinVer1 OBJECT-TYPE
    SYNTAX       SnmpAdminString
    MAX-ACCESS   read-only
    STATUS       current
    DESCRIPTION
        "Cisco Firepower equipment:FirmwareConstraint:minVer1
        managed object property"
    ::= { cfprEquipmentFirmwareConstraintEntry 4 }

cfprEquipmentFirmwareConstraintMinVer2 OBJECT-TYPE
    SYNTAX       SnmpAdminString
    MAX-ACCESS   read-only
    STATUS       current
    DESCRIPTION
        "Cisco Firepower equipment:FirmwareConstraint:minVer2
        managed object property"
    ::= { cfprEquipmentFirmwareConstraintEntry 5 }

cfprEquipmentFlashLifeTable OBJECT-TYPE
    SYNTAX           SEQUENCE OF CfprEquipmentFlashLifeEntry
    MAX-ACCESS       not-accessible
    STATUS           current
    DESCRIPTION
        "Cisco Firepower equipment:FlashLife managed object table"
    ::= { cfprEquipmentObjects 54 }

cfprEquipmentFlashLifeEntry OBJECT-TYPE
    SYNTAX           CfprEquipmentFlashLifeEntry
    MAX-ACCESS       not-accessible
    STATUS           current
    DESCRIPTION
        "Entry for the cfprEquipmentFlashLifeTable table."
    INDEX { cfprEquipmentFlashLifeInstanceId }
    ::= { cfprEquipmentFlashLifeTable 1 }

CfprEquipmentFlashLifeEntry ::= SEQUENCE {
    cfprEquipmentFlashLifeInstanceId                                 CfprManagedObjectId,
    cfprEquipmentFlashLifeDn                                         CfprManagedObjectDn,
    cfprEquipmentFlashLifeRn                                         SnmpAdminString,
    cfprEquipmentFlashLifeCardParamType                              Gauge32,
    cfprEquipmentFlashLifeDescr                                      SnmpAdminString,
    cfprEquipmentFlashLifeIntId                                      SnmpAdminString,
    cfprEquipmentFlashLifeName                                       SnmpAdminString,
    cfprEquipmentFlashLifePolicyLevel                                Gauge32,
    cfprEquipmentFlashLifePolicyOwner                                CfprPolicyPolicyOwner,
    cfprEquipmentFlashLifeSuportType                                 Gauge32
}

cfprEquipmentFlashLifeInstanceId OBJECT-TYPE
    SYNTAX       CfprManagedObjectId
    MAX-ACCESS   not-accessible
    STATUS       current
    DESCRIPTION
        "Instance identifier of the managed object."
    ::= { cfprEquipmentFlashLifeEntry 1 }

cfprEquipmentFlashLifeDn OBJECT-TYPE
    SYNTAX       CfprManagedObjectDn
    MAX-ACCESS   read-only
    STATUS       current
    DESCRIPTION
        "Cisco Firepower equipment:FlashLife:dn managed object property"
    ::= { cfprEquipmentFlashLifeEntry 2 }

cfprEquipmentFlashLifeRn OBJECT-TYPE
    SYNTAX       SnmpAdminString
    MAX-ACCESS   read-only
    STATUS       current
    DESCRIPTION
        "Cisco Firepower equipment:FlashLife:rn managed object property"
    ::= { cfprEquipmentFlashLifeEntry 3 }

cfprEquipmentFlashLifeCardParamType OBJECT-TYPE
    SYNTAX       Gauge32
    MAX-ACCESS   read-only
    STATUS       current
    DESCRIPTION
        "Cisco Firepower equipment:FlashLife:cardParamType
        managed object property"
    ::= { cfprEquipmentFlashLifeEntry 4 }

cfprEquipmentFlashLifeDescr OBJECT-TYPE
    SYNTAX       SnmpAdminString
    MAX-ACCESS   read-only
    STATUS       current
    DESCRIPTION
        "Cisco Firepower equipment:FlashLife:descr managed
        object property"
    ::= { cfprEquipmentFlashLifeEntry 5 }

cfprEquipmentFlashLifeIntId OBJECT-TYPE
    SYNTAX       SnmpAdminString
    MAX-ACCESS   read-only
    STATUS       current
    DESCRIPTION
        "Cisco Firepower equipment:FlashLife:intId managed
        object property"
    ::= { cfprEquipmentFlashLifeEntry 6 }

cfprEquipmentFlashLifeName OBJECT-TYPE
    SYNTAX       SnmpAdminString
    MAX-ACCESS   read-only
    STATUS       current
    DESCRIPTION
        "Cisco Firepower equipment:FlashLife:name managed object property"
    ::= { cfprEquipmentFlashLifeEntry 7 }

cfprEquipmentFlashLifePolicyLevel OBJECT-TYPE
    SYNTAX       Gauge32
    MAX-ACCESS   read-only
    STATUS       current
    DESCRIPTION
        "Cisco Firepower equipment:FlashLife:policyLevel
        managed object property"
    ::= { cfprEquipmentFlashLifeEntry 8 }

cfprEquipmentFlashLifePolicyOwner OBJECT-TYPE
    SYNTAX       CfprPolicyPolicyOwner
    MAX-ACCESS   read-only
    STATUS       current
    DESCRIPTION
        "Cisco Firepower equipment:FlashLife:policyOwner
        managed object property"
    ::= { cfprEquipmentFlashLifeEntry 9 }

cfprEquipmentFlashLifeSuportType OBJECT-TYPE
    SYNTAX       Gauge32
    MAX-ACCESS   read-only
    STATUS       current
    DESCRIPTION
        "Cisco Firepower equipment:FlashLife:suportType
        managed object property"
    ::= { cfprEquipmentFlashLifeEntry 10 }

cfprEquipmentFpgaTable OBJECT-TYPE
    SYNTAX           SEQUENCE OF CfprEquipmentFpgaEntry
    MAX-ACCESS       not-accessible
    STATUS           current
    DESCRIPTION
        "Cisco Firepower equipment:Fpga managed object table"
    ::= { cfprEquipmentObjects 154 }

cfprEquipmentFpgaEntry OBJECT-TYPE
    SYNTAX           CfprEquipmentFpgaEntry
    MAX-ACCESS       not-accessible
    STATUS           current
    DESCRIPTION
        "Entry for the cfprEquipmentFpgaTable table."
    INDEX { cfprEquipmentFpgaInstanceId }
    ::= { cfprEquipmentFpgaTable 1 }

CfprEquipmentFpgaEntry ::= SEQUENCE {
    cfprEquipmentFpgaInstanceId                                      CfprManagedObjectId,
    cfprEquipmentFpgaDn                                              CfprManagedObjectDn,
    cfprEquipmentFpgaRn                                              SnmpAdminString,
    cfprEquipmentFpgaBkupPackageVersion                              SnmpAdminString,
    cfprEquipmentFpgaBkupVersion                                     SnmpAdminString,
    cfprEquipmentFpgaFltAggr                                         Unsigned64,
    cfprEquipmentFpgaIsUpgradable                                    TruthValue,
    cfprEquipmentFpgaModel                                           SnmpAdminString,
    cfprEquipmentFpgaRevision                                        SnmpAdminString,
    cfprEquipmentFpgaSerial                                          SnmpAdminString,
    cfprEquipmentFpgaUpgradeStatus                                   SnmpAdminString,
    cfprEquipmentFpgaVendor                                          SnmpAdminString,
    cfprEquipmentFpgaIsUpgradeRequired                               TruthValue
}

cfprEquipmentFpgaInstanceId OBJECT-TYPE
    SYNTAX       CfprManagedObjectId
    MAX-ACCESS   not-accessible
    STATUS       current
    DESCRIPTION
        "Instance identifier of the managed object."
    ::= { cfprEquipmentFpgaEntry 1 }

cfprEquipmentFpgaDn OBJECT-TYPE
    SYNTAX       CfprManagedObjectDn
    MAX-ACCESS   read-only
    STATUS       current
    DESCRIPTION
        "Cisco Firepower equipment:Fpga:dn managed object property"
    ::= { cfprEquipmentFpgaEntry 2 }

cfprEquipmentFpgaRn OBJECT-TYPE
    SYNTAX       SnmpAdminString
    MAX-ACCESS   read-only
    STATUS       current
    DESCRIPTION
        "Cisco Firepower equipment:Fpga:rn managed object property"
    ::= { cfprEquipmentFpgaEntry 3 }

cfprEquipmentFpgaBkupPackageVersion OBJECT-TYPE
    SYNTAX       SnmpAdminString
    MAX-ACCESS   read-only
    STATUS       current
    DESCRIPTION
        "Cisco Firepower equipment:Fpga:bkupPackageVersion
        managed object property"
    ::= { cfprEquipmentFpgaEntry 4 }

cfprEquipmentFpgaBkupVersion OBJECT-TYPE
    SYNTAX       SnmpAdminString
    MAX-ACCESS   read-only
    STATUS       current
    DESCRIPTION
        "Cisco Firepower equipment:Fpga:bkupVersion managed
        object property"
    ::= { cfprEquipmentFpgaEntry 5 }

cfprEquipmentFpgaFltAggr OBJECT-TYPE
    SYNTAX       Unsigned64
    MAX-ACCESS   read-only
    STATUS       current
    DESCRIPTION
        "Cisco Firepower equipment:Fpga:fltAggr managed object property"
    ::= { cfprEquipmentFpgaEntry 6 }

cfprEquipmentFpgaIsUpgradable OBJECT-TYPE
    SYNTAX       TruthValue
    MAX-ACCESS   read-only
    STATUS       current
    DESCRIPTION
        "Cisco Firepower equipment:Fpga:isUpgradable managed
        object property"
    ::= { cfprEquipmentFpgaEntry 7 }

cfprEquipmentFpgaModel OBJECT-TYPE
    SYNTAX       SnmpAdminString
    MAX-ACCESS   read-only
    STATUS       current
    DESCRIPTION
        "Cisco Firepower equipment:Fpga:model managed object property"
    ::= { cfprEquipmentFpgaEntry 8 }

cfprEquipmentFpgaRevision OBJECT-TYPE
    SYNTAX       SnmpAdminString
    MAX-ACCESS   read-only
    STATUS       current
    DESCRIPTION
        "Cisco Firepower equipment:Fpga:revision managed object property"
    ::= { cfprEquipmentFpgaEntry 9 }

cfprEquipmentFpgaSerial OBJECT-TYPE
    SYNTAX       SnmpAdminString
    MAX-ACCESS   read-only
    STATUS       current
    DESCRIPTION
        "Cisco Firepower equipment:Fpga:serial managed object property"
    ::= { cfprEquipmentFpgaEntry 10 }

cfprEquipmentFpgaUpgradeStatus OBJECT-TYPE
    SYNTAX       SnmpAdminString
    MAX-ACCESS   read-only
    STATUS       current
    DESCRIPTION
        "Cisco Firepower equipment:Fpga:upgradeStatus managed
        object property"
    ::= { cfprEquipmentFpgaEntry 11 }

cfprEquipmentFpgaVendor OBJECT-TYPE
    SYNTAX       SnmpAdminString
    MAX-ACCESS   read-only
    STATUS       current
    DESCRIPTION
        "Cisco Firepower equipment:Fpga:vendor managed object property"
    ::= { cfprEquipmentFpgaEntry 12 }

cfprEquipmentFpgaIsUpgradeRequired OBJECT-TYPE
    SYNTAX       TruthValue
    MAX-ACCESS   read-only
    STATUS       current
    DESCRIPTION
        "Cisco Firepower equipment:Fpga:isUpgradeRequired
        managed object property"
    ::= { cfprEquipmentFpgaEntry 13 }

cfprEquipmentGemCapProviderTable OBJECT-TYPE
    SYNTAX           SEQUENCE OF CfprEquipmentGemCapProviderEntry
    MAX-ACCESS       not-accessible
    STATUS           current
    DESCRIPTION
        "Cisco Firepower equipment:GemCapProvider managed object table"
    ::= { cfprEquipmentObjects 55 }

cfprEquipmentGemCapProviderEntry OBJECT-TYPE
    SYNTAX           CfprEquipmentGemCapProviderEntry
    MAX-ACCESS       not-accessible
    STATUS           current
    DESCRIPTION
        "Entry for the cfprEquipmentGemCapProviderTable table."
    INDEX { cfprEquipmentGemCapProviderInstanceId }
    ::= { cfprEquipmentGemCapProviderTable 1 }

CfprEquipmentGemCapProviderEntry ::= SEQUENCE {
    cfprEquipmentGemCapProviderInstanceId                            CfprManagedObjectId,
    cfprEquipmentGemCapProviderDn                                    CfprManagedObjectDn,
    cfprEquipmentGemCapProviderRn                                    SnmpAdminString,
    cfprEquipmentGemCapProviderDeleted                               TruthValue,
    cfprEquipmentGemCapProviderDeprecated                            TruthValue,
    cfprEquipmentGemCapProviderElementLoadFailures                   Gauge32,
    cfprEquipmentGemCapProviderElementsLoaded                        Gauge32,
    cfprEquipmentGemCapProviderGencount                              Gauge32,
    cfprEquipmentGemCapProviderLoadErrors                            Gauge32,
    cfprEquipmentGemCapProviderLoadWarnings                          Gauge32,
    cfprEquipmentGemCapProviderMgmtPlaneVer                          SnmpAdminString,
    cfprEquipmentGemCapProviderModel                                 SnmpAdminString,
    cfprEquipmentGemCapProviderPromCardType                          Gauge32,
    cfprEquipmentGemCapProviderRevision                              SnmpAdminString,
    cfprEquipmentGemCapProviderVendor                                SnmpAdminString,
    cfprEquipmentGemCapProviderMaxUserPort                           Gauge32,
    cfprEquipmentGemCapProviderOir                                   TruthValue
}

cfprEquipmentGemCapProviderInstanceId OBJECT-TYPE
    SYNTAX       CfprManagedObjectId
    MAX-ACCESS   not-accessible
    STATUS       current
    DESCRIPTION
        "Instance identifier of the managed object."
    ::= { cfprEquipmentGemCapProviderEntry 1 }

cfprEquipmentGemCapProviderDn OBJECT-TYPE
    SYNTAX       CfprManagedObjectDn
    MAX-ACCESS   read-only
    STATUS       current
    DESCRIPTION
        "Cisco Firepower equipment:GemCapProvider:dn managed
        object property"
    ::= { cfprEquipmentGemCapProviderEntry 2 }

cfprEquipmentGemCapProviderRn OBJECT-TYPE
    SYNTAX       SnmpAdminString
    MAX-ACCESS   read-only
    STATUS       current
    DESCRIPTION
        "Cisco Firepower equipment:GemCapProvider:rn managed
        object property"
    ::= { cfprEquipmentGemCapProviderEntry 3 }

cfprEquipmentGemCapProviderDeleted OBJECT-TYPE
    SYNTAX       TruthValue
    MAX-ACCESS   read-only
    STATUS       current
    DESCRIPTION
        "Cisco Firepower equipment:GemCapProvider:deleted
        managed object property"
    ::= { cfprEquipmentGemCapProviderEntry 4 }

cfprEquipmentGemCapProviderDeprecated OBJECT-TYPE
    SYNTAX       TruthValue
    MAX-ACCESS   read-only
    STATUS       current
    DESCRIPTION
        "Cisco Firepower equipment:GemCapProvider:deprecated
        managed object property"
    ::= { cfprEquipmentGemCapProviderEntry 5 }

cfprEquipmentGemCapProviderElementLoadFailures OBJECT-TYPE
    SYNTAX       Gauge32
    MAX-ACCESS   read-only
    STATUS       current
    DESCRIPTION
        "Cisco Firepower equipment:GemCapProvider:elementLoadFailures
        managed object property"
    ::= { cfprEquipmentGemCapProviderEntry 6 }

cfprEquipmentGemCapProviderElementsLoaded OBJECT-TYPE
    SYNTAX       Gauge32
    MAX-ACCESS   read-only
    STATUS       current
    DESCRIPTION
        "Cisco Firepower equipment:GemCapProvider:elementsLoaded
        managed object property"
    ::= { cfprEquipmentGemCapProviderEntry 7 }

cfprEquipmentGemCapProviderGencount OBJECT-TYPE
    SYNTAX       Gauge32
    MAX-ACCESS   read-only
    STATUS       current
    DESCRIPTION
        "Cisco Firepower equipment:GemCapProvider:gencount
        managed object property"
    ::= { cfprEquipmentGemCapProviderEntry 8 }

cfprEquipmentGemCapProviderLoadErrors OBJECT-TYPE
    SYNTAX       Gauge32
    MAX-ACCESS   read-only
    STATUS       current
    DESCRIPTION
        "Cisco Firepower equipment:GemCapProvider:loadErrors
        managed object property"
    ::= { cfprEquipmentGemCapProviderEntry 9 }

cfprEquipmentGemCapProviderLoadWarnings OBJECT-TYPE
    SYNTAX       Gauge32
    MAX-ACCESS   read-only
    STATUS       current
    DESCRIPTION
        "Cisco Firepower equipment:GemCapProvider:loadWarnings
        managed object property"
    ::= { cfprEquipmentGemCapProviderEntry 10 }

cfprEquipmentGemCapProviderMgmtPlaneVer OBJECT-TYPE
    SYNTAX       SnmpAdminString
    MAX-ACCESS   read-only
    STATUS       current
    DESCRIPTION
        "Cisco Firepower equipment:GemCapProvider:mgmtPlaneVer
        managed object property"
    ::= { cfprEquipmentGemCapProviderEntry 11 }

cfprEquipmentGemCapProviderModel OBJECT-TYPE
    SYNTAX       SnmpAdminString
    MAX-ACCESS   read-only
    STATUS       current
    DESCRIPTION
        "Cisco Firepower equipment:GemCapProvider:model
        managed object property"
    ::= { cfprEquipmentGemCapProviderEntry 12 }

cfprEquipmentGemCapProviderPromCardType OBJECT-TYPE
    SYNTAX       Gauge32
    MAX-ACCESS   read-only
    STATUS       current
    DESCRIPTION
        "Cisco Firepower equipment:GemCapProvider:promCardType
        managed object property"
    ::= { cfprEquipmentGemCapProviderEntry 13 }

cfprEquipmentGemCapProviderRevision OBJECT-TYPE
    SYNTAX       SnmpAdminString
    MAX-ACCESS   read-only
    STATUS       current
    DESCRIPTION
        "Cisco Firepower equipment:GemCapProvider:revision
        managed object property"
    ::= { cfprEquipmentGemCapProviderEntry 14 }

cfprEquipmentGemCapProviderVendor OBJECT-TYPE
    SYNTAX       SnmpAdminString
    MAX-ACCESS   read-only
    STATUS       current
    DESCRIPTION
        "Cisco Firepower equipment:GemCapProvider:vendor
        managed object property"
    ::= { cfprEquipmentGemCapProviderEntry 15 }

cfprEquipmentGemCapProviderMaxUserPort OBJECT-TYPE
    SYNTAX       Gauge32
    MAX-ACCESS   read-only
    STATUS       current
    DESCRIPTION
        "Cisco Firepower equipment:GemCapProvider:maxUserPort
        managed object property"
    ::= { cfprEquipmentGemCapProviderEntry 16 }

cfprEquipmentGemCapProviderOir OBJECT-TYPE
    SYNTAX       TruthValue
    MAX-ACCESS   read-only
    STATUS       current
    DESCRIPTION
        "Cisco Firepower equipment:GemCapProvider:oir managed
        object property"
    ::= { cfprEquipmentGemCapProviderEntry 17 }

cfprEquipmentGemPortCapTable OBJECT-TYPE
    SYNTAX           SEQUENCE OF CfprEquipmentGemPortCapEntry
    MAX-ACCESS       not-accessible
    STATUS           current
    DESCRIPTION
        "Cisco Firepower equipment:GemPortCap managed object table"
    ::= { cfprEquipmentObjects 56 }

cfprEquipmentGemPortCapEntry OBJECT-TYPE
    SYNTAX           CfprEquipmentGemPortCapEntry
    MAX-ACCESS       not-accessible
    STATUS           current
    DESCRIPTION
        "Entry for the cfprEquipmentGemPortCapTable table."
    INDEX { cfprEquipmentGemPortCapInstanceId }
    ::= { cfprEquipmentGemPortCapTable 1 }

CfprEquipmentGemPortCapEntry ::= SEQUENCE {
    cfprEquipmentGemPortCapInstanceId                                CfprManagedObjectId,
    cfprEquipmentGemPortCapDn                                        CfprManagedObjectDn,
    cfprEquipmentGemPortCapRn                                        SnmpAdminString,
    cfprEquipmentGemPortCapDescr                                     SnmpAdminString,
    cfprEquipmentGemPortCapIntId                                     SnmpAdminString,
    cfprEquipmentGemPortCapMaxFcSpeed                                CfprPortSpeed,
    cfprEquipmentGemPortCapName                                      SnmpAdminString,
    cfprEquipmentGemPortCapPolicyLevel                               Gauge32,
    cfprEquipmentGemPortCapPolicyOwner                               CfprPolicyPolicyOwner,
    cfprEquipmentGemPortCapPortNumber                                Gauge32,
    cfprEquipmentGemPortCapMediaType                                 CfprEquipmentMediaType,
    cfprEquipmentGemPortCapPortSpeedCap                              CfprEquipmentEthPortSpeedCap
}

cfprEquipmentGemPortCapInstanceId OBJECT-TYPE
    SYNTAX       CfprManagedObjectId
    MAX-ACCESS   not-accessible
    STATUS       current
    DESCRIPTION
        "Instance identifier of the managed object."
    ::= { cfprEquipmentGemPortCapEntry 1 }

cfprEquipmentGemPortCapDn OBJECT-TYPE
    SYNTAX       CfprManagedObjectDn
    MAX-ACCESS   read-only
    STATUS       current
    DESCRIPTION
        "Cisco Firepower equipment:GemPortCap:dn managed object property"
    ::= { cfprEquipmentGemPortCapEntry 2 }

cfprEquipmentGemPortCapRn OBJECT-TYPE
    SYNTAX       SnmpAdminString
    MAX-ACCESS   read-only
    STATUS       current
    DESCRIPTION
        "Cisco Firepower equipment:GemPortCap:rn managed object property"
    ::= { cfprEquipmentGemPortCapEntry 3 }

cfprEquipmentGemPortCapDescr OBJECT-TYPE
    SYNTAX       SnmpAdminString
    MAX-ACCESS   read-only
    STATUS       current
    DESCRIPTION
        "Cisco Firepower equipment:GemPortCap:descr managed
        object property"
    ::= { cfprEquipmentGemPortCapEntry 4 }

cfprEquipmentGemPortCapIntId OBJECT-TYPE
    SYNTAX       SnmpAdminString
    MAX-ACCESS   read-only
    STATUS       current
    DESCRIPTION
        "Cisco Firepower equipment:GemPortCap:intId managed
        object property"
    ::= { cfprEquipmentGemPortCapEntry 5 }

cfprEquipmentGemPortCapMaxFcSpeed OBJECT-TYPE
    SYNTAX       CfprPortSpeed
    MAX-ACCESS   read-only
    STATUS       current
    DESCRIPTION
        "Cisco Firepower equipment:GemPortCap:maxFcSpeed
        managed object property"
    ::= { cfprEquipmentGemPortCapEntry 6 }

cfprEquipmentGemPortCapName OBJECT-TYPE
    SYNTAX       SnmpAdminString
    MAX-ACCESS   read-only
    STATUS       current
    DESCRIPTION
        "Cisco Firepower equipment:GemPortCap:name managed
        object property"
    ::= { cfprEquipmentGemPortCapEntry 7 }

cfprEquipmentGemPortCapPolicyLevel OBJECT-TYPE
    SYNTAX       Gauge32
    MAX-ACCESS   read-only
    STATUS       current
    DESCRIPTION
        "Cisco Firepower equipment:GemPortCap:policyLevel
        managed object property"
    ::= { cfprEquipmentGemPortCapEntry 8 }

cfprEquipmentGemPortCapPolicyOwner OBJECT-TYPE
    SYNTAX       CfprPolicyPolicyOwner
    MAX-ACCESS   read-only
    STATUS       current
    DESCRIPTION
        "Cisco Firepower equipment:GemPortCap:policyOwner
        managed object property"
    ::= { cfprEquipmentGemPortCapEntry 9 }

cfprEquipmentGemPortCapPortNumber OBJECT-TYPE
    SYNTAX       Gauge32
    MAX-ACCESS   read-only
    STATUS       current
    DESCRIPTION
        "Cisco Firepower equipment:GemPortCap:portNumber
        managed object property"
    ::= { cfprEquipmentGemPortCapEntry 10 }

cfprEquipmentGemPortCapMediaType OBJECT-TYPE
    SYNTAX       CfprEquipmentMediaType
    MAX-ACCESS   read-only
    STATUS       current
    DESCRIPTION
        "Cisco Firepower equipment:GemPortCap:mediaType
        managed object property"
    ::= { cfprEquipmentGemPortCapEntry 11 }

cfprEquipmentGemPortCapPortSpeedCap OBJECT-TYPE
    SYNTAX       CfprEquipmentEthPortSpeedCap
    MAX-ACCESS   read-only
    STATUS       current
    DESCRIPTION
        "Cisco Firepower equipment:GemPortCap:portSpeedCap
        managed object property"
    ::= { cfprEquipmentGemPortCapEntry 12 }

cfprEquipmentGraphicsCardCapProviderTable OBJECT-TYPE
    SYNTAX           SEQUENCE OF CfprEquipmentGraphicsCardCapProviderEntry
    MAX-ACCESS       not-accessible
    STATUS           current
    DESCRIPTION
        "Cisco Firepower equipment:GraphicsCardCapProvider
        managed object table"
    ::= { cfprEquipmentObjects 57 }

cfprEquipmentGraphicsCardCapProviderEntry OBJECT-TYPE
    SYNTAX           CfprEquipmentGraphicsCardCapProviderEntry
    MAX-ACCESS       not-accessible
    STATUS           current
    DESCRIPTION
        "Entry for the cfprEquipmentGraphicsCardCapProviderTable table."
    INDEX { cfprEquipmentGraphicsCardCapProviderInstanceId }
    ::= { cfprEquipmentGraphicsCardCapProviderTable 1 }

CfprEquipmentGraphicsCardCapProviderEntry ::= SEQUENCE {
    cfprEquipmentGraphicsCardCapProviderInstanceId                   CfprManagedObjectId,
    cfprEquipmentGraphicsCardCapProviderDn                           CfprManagedObjectDn,
    cfprEquipmentGraphicsCardCapProviderRn                           SnmpAdminString,
    cfprEquipmentGraphicsCardCapProviderDeleted                      TruthValue,
    cfprEquipmentGraphicsCardCapProviderDeprecated                   TruthValue,
    cfprEquipmentGraphicsCardCapProviderElementLoadFailures          Gauge32,
    cfprEquipmentGraphicsCardCapProviderElementsLoaded               Gauge32,
    cfprEquipmentGraphicsCardCapProviderGencount                     Gauge32,
    cfprEquipmentGraphicsCardCapProviderLoadErrors                   Gauge32,
    cfprEquipmentGraphicsCardCapProviderLoadWarnings                 Gauge32,
    cfprEquipmentGraphicsCardCapProviderMgmtPlaneVer                 SnmpAdminString,
    cfprEquipmentGraphicsCardCapProviderModel                        SnmpAdminString,
    cfprEquipmentGraphicsCardCapProviderNumGpu                       Gauge32,
    cfprEquipmentGraphicsCardCapProviderPromCardType                 Gauge32,
    cfprEquipmentGraphicsCardCapProviderRevision                     SnmpAdminString,
    cfprEquipmentGraphicsCardCapProviderVendor                       SnmpAdminString
}

cfprEquipmentGraphicsCardCapProviderInstanceId OBJECT-TYPE
    SYNTAX       CfprManagedObjectId
    MAX-ACCESS   not-accessible
    STATUS       current
    DESCRIPTION
        "Instance identifier of the managed object."
    ::= { cfprEquipmentGraphicsCardCapProviderEntry 1 }

cfprEquipmentGraphicsCardCapProviderDn OBJECT-TYPE
    SYNTAX       CfprManagedObjectDn
    MAX-ACCESS   read-only
    STATUS       current
    DESCRIPTION
        "Cisco Firepower equipment:GraphicsCardCapProvider:dn
        managed object property"
    ::= { cfprEquipmentGraphicsCardCapProviderEntry 2 }

cfprEquipmentGraphicsCardCapProviderRn OBJECT-TYPE
    SYNTAX       SnmpAdminString
    MAX-ACCESS   read-only
    STATUS       current
    DESCRIPTION
        "Cisco Firepower equipment:GraphicsCardCapProvider:rn
        managed object property"
    ::= { cfprEquipmentGraphicsCardCapProviderEntry 3 }

cfprEquipmentGraphicsCardCapProviderDeleted OBJECT-TYPE
    SYNTAX       TruthValue
    MAX-ACCESS   read-only
    STATUS       current
    DESCRIPTION
        "Cisco Firepower equipment:GraphicsCardCapProvider:deleted
        managed object property"
    ::= { cfprEquipmentGraphicsCardCapProviderEntry 4 }

cfprEquipmentGraphicsCardCapProviderDeprecated OBJECT-TYPE
    SYNTAX       TruthValue
    MAX-ACCESS   read-only
    STATUS       current
    DESCRIPTION
        "Cisco Firepower equipment:GraphicsCardCapProvider:deprecated
        managed object property"
    ::= { cfprEquipmentGraphicsCardCapProviderEntry 5 }

cfprEquipmentGraphicsCardCapProviderElementLoadFailures OBJECT-TYPE
    SYNTAX       Gauge32
    MAX-ACCESS   read-only
    STATUS       current
    DESCRIPTION
        "Cisco Firepower equipment:GraphicsCardCapProvider:elementLoadFail
        ures managed object property"
    ::= { cfprEquipmentGraphicsCardCapProviderEntry 6 }

cfprEquipmentGraphicsCardCapProviderElementsLoaded OBJECT-TYPE
    SYNTAX       Gauge32
    MAX-ACCESS   read-only
    STATUS       current
    DESCRIPTION
        "Cisco Firepower equipment:GraphicsCardCapProvider:elementsLoaded
        managed object property"
    ::= { cfprEquipmentGraphicsCardCapProviderEntry 7 }

cfprEquipmentGraphicsCardCapProviderGencount OBJECT-TYPE
    SYNTAX       Gauge32
    MAX-ACCESS   read-only
    STATUS       current
    DESCRIPTION
        "Cisco Firepower equipment:GraphicsCardCapProvider:gencount
        managed object property"
    ::= { cfprEquipmentGraphicsCardCapProviderEntry 8 }

cfprEquipmentGraphicsCardCapProviderLoadErrors OBJECT-TYPE
    SYNTAX       Gauge32
    MAX-ACCESS   read-only
    STATUS       current
    DESCRIPTION
        "Cisco Firepower equipment:GraphicsCardCapProvider:loadErrors
        managed object property"
    ::= { cfprEquipmentGraphicsCardCapProviderEntry 9 }

cfprEquipmentGraphicsCardCapProviderLoadWarnings OBJECT-TYPE
    SYNTAX       Gauge32
    MAX-ACCESS   read-only
    STATUS       current
    DESCRIPTION
        "Cisco Firepower equipment:GraphicsCardCapProvider:loadWarnings
        managed object property"
    ::= { cfprEquipmentGraphicsCardCapProviderEntry 10 }

cfprEquipmentGraphicsCardCapProviderMgmtPlaneVer OBJECT-TYPE
    SYNTAX       SnmpAdminString
    MAX-ACCESS   read-only
    STATUS       current
    DESCRIPTION
        "Cisco Firepower equipment:GraphicsCardCapProvider:mgmtPlaneVer
        managed object property"
    ::= { cfprEquipmentGraphicsCardCapProviderEntry 11 }

cfprEquipmentGraphicsCardCapProviderModel OBJECT-TYPE
    SYNTAX       SnmpAdminString
    MAX-ACCESS   read-only
    STATUS       current
    DESCRIPTION
        "Cisco Firepower equipment:GraphicsCardCapProvider:model
        managed object property"
    ::= { cfprEquipmentGraphicsCardCapProviderEntry 12 }

cfprEquipmentGraphicsCardCapProviderNumGpu OBJECT-TYPE
    SYNTAX       Gauge32
    MAX-ACCESS   read-only
    STATUS       current
    DESCRIPTION
        "Cisco Firepower equipment:GraphicsCardCapProvider:numGpu
        managed object property"
    ::= { cfprEquipmentGraphicsCardCapProviderEntry 13 }

cfprEquipmentGraphicsCardCapProviderPromCardType OBJECT-TYPE
    SYNTAX       Gauge32
    MAX-ACCESS   read-only
    STATUS       current
    DESCRIPTION
        "Cisco Firepower equipment:GraphicsCardCapProvider:promCardType
        managed object property"
    ::= { cfprEquipmentGraphicsCardCapProviderEntry 14 }

cfprEquipmentGraphicsCardCapProviderRevision OBJECT-TYPE
    SYNTAX       SnmpAdminString
    MAX-ACCESS   read-only
    STATUS       current
    DESCRIPTION
        "Cisco Firepower equipment:GraphicsCardCapProvider:revision
        managed object property"
    ::= { cfprEquipmentGraphicsCardCapProviderEntry 15 }

cfprEquipmentGraphicsCardCapProviderVendor OBJECT-TYPE
    SYNTAX       SnmpAdminString
    MAX-ACCESS   read-only
    STATUS       current
    DESCRIPTION
        "Cisco Firepower equipment:GraphicsCardCapProvider:vendor
        managed object property"
    ::= { cfprEquipmentGraphicsCardCapProviderEntry 16 }

cfprEquipmentGraphicsCardCapRefTable OBJECT-TYPE
    SYNTAX           SEQUENCE OF CfprEquipmentGraphicsCardCapRefEntry
    MAX-ACCESS       not-accessible
    STATUS           current
    DESCRIPTION
        "Cisco Firepower equipment:GraphicsCardCapRef managed
        object table"
    ::= { cfprEquipmentObjects 58 }

cfprEquipmentGraphicsCardCapRefEntry OBJECT-TYPE
    SYNTAX           CfprEquipmentGraphicsCardCapRefEntry
    MAX-ACCESS       not-accessible
    STATUS           current
    DESCRIPTION
        "Entry for the cfprEquipmentGraphicsCardCapRefTable table."
    INDEX { cfprEquipmentGraphicsCardCapRefInstanceId }
    ::= { cfprEquipmentGraphicsCardCapRefTable 1 }

CfprEquipmentGraphicsCardCapRefEntry ::= SEQUENCE {
    cfprEquipmentGraphicsCardCapRefInstanceId                        CfprManagedObjectId,
    cfprEquipmentGraphicsCardCapRefDn                                CfprManagedObjectDn,
    cfprEquipmentGraphicsCardCapRefRn                                SnmpAdminString,
    cfprEquipmentGraphicsCardCapRefModel                             SnmpAdminString,
    cfprEquipmentGraphicsCardCapRefRevision                          SnmpAdminString,
    cfprEquipmentGraphicsCardCapRefVendor                            SnmpAdminString
}

cfprEquipmentGraphicsCardCapRefInstanceId OBJECT-TYPE
    SYNTAX       CfprManagedObjectId
    MAX-ACCESS   not-accessible
    STATUS       current
    DESCRIPTION
        "Instance identifier of the managed object."
    ::= { cfprEquipmentGraphicsCardCapRefEntry 1 }

cfprEquipmentGraphicsCardCapRefDn OBJECT-TYPE
    SYNTAX       CfprManagedObjectDn
    MAX-ACCESS   read-only
    STATUS       current
    DESCRIPTION
        "Cisco Firepower equipment:GraphicsCardCapRef:dn
        managed object property"
    ::= { cfprEquipmentGraphicsCardCapRefEntry 2 }

cfprEquipmentGraphicsCardCapRefRn OBJECT-TYPE
    SYNTAX       SnmpAdminString
    MAX-ACCESS   read-only
    STATUS       current
    DESCRIPTION
        "Cisco Firepower equipment:GraphicsCardCapRef:rn
        managed object property"
    ::= { cfprEquipmentGraphicsCardCapRefEntry 3 }

cfprEquipmentGraphicsCardCapRefModel OBJECT-TYPE
    SYNTAX       SnmpAdminString
    MAX-ACCESS   read-only
    STATUS       current
    DESCRIPTION
        "Cisco Firepower equipment:GraphicsCardCapRef:model
        managed object property"
    ::= { cfprEquipmentGraphicsCardCapRefEntry 4 }

cfprEquipmentGraphicsCardCapRefRevision OBJECT-TYPE
    SYNTAX       SnmpAdminString
    MAX-ACCESS   read-only
    STATUS       current
    DESCRIPTION
        "Cisco Firepower equipment:GraphicsCardCapRef:revision
        managed object property"
    ::= { cfprEquipmentGraphicsCardCapRefEntry 5 }

cfprEquipmentGraphicsCardCapRefVendor OBJECT-TYPE
    SYNTAX       SnmpAdminString
    MAX-ACCESS   read-only
    STATUS       current
    DESCRIPTION
        "Cisco Firepower equipment:GraphicsCardCapRef:vendor
        managed object property"
    ::= { cfprEquipmentGraphicsCardCapRefEntry 6 }

cfprEquipmentHDDFaultMonDefTable OBJECT-TYPE
    SYNTAX           SEQUENCE OF CfprEquipmentHDDFaultMonDefEntry
    MAX-ACCESS       not-accessible
    STATUS           current
    DESCRIPTION
        "Cisco Firepower equipment:HDDFaultMonDef managed object table"
    ::= { cfprEquipmentObjects 59 }

cfprEquipmentHDDFaultMonDefEntry OBJECT-TYPE
    SYNTAX           CfprEquipmentHDDFaultMonDefEntry
    MAX-ACCESS       not-accessible
    STATUS           current
    DESCRIPTION
        "Entry for the cfprEquipmentHDDFaultMonDefTable table."
    INDEX { cfprEquipmentHDDFaultMonDefInstanceId }
    ::= { cfprEquipmentHDDFaultMonDefTable 1 }

CfprEquipmentHDDFaultMonDefEntry ::= SEQUENCE {
    cfprEquipmentHDDFaultMonDefInstanceId                            CfprManagedObjectId,
    cfprEquipmentHDDFaultMonDefDn                                    CfprManagedObjectDn,
    cfprEquipmentHDDFaultMonDefRn                                    SnmpAdminString,
    cfprEquipmentHDDFaultMonDefControllerFwVersion                   SnmpAdminString,
    cfprEquipmentHDDFaultMonDefControllerModel                       SnmpAdminString,
    cfprEquipmentHDDFaultMonDefHDDMonSupport                         SnmpAdminString,
    cfprEquipmentHDDFaultMonDefDescr                                 SnmpAdminString,
    cfprEquipmentHDDFaultMonDefIntId                                 SnmpAdminString,
    cfprEquipmentHDDFaultMonDefName                                  SnmpAdminString,
    cfprEquipmentHDDFaultMonDefPolicyLevel                           Gauge32,
    cfprEquipmentHDDFaultMonDefPolicyOwner                           CfprPolicyPolicyOwner
}

cfprEquipmentHDDFaultMonDefInstanceId OBJECT-TYPE
    SYNTAX       CfprManagedObjectId
    MAX-ACCESS   not-accessible
    STATUS       current
    DESCRIPTION
        "Instance identifier of the managed object."
    ::= { cfprEquipmentHDDFaultMonDefEntry 1 }

cfprEquipmentHDDFaultMonDefDn OBJECT-TYPE
    SYNTAX       CfprManagedObjectDn
    MAX-ACCESS   read-only
    STATUS       current
    DESCRIPTION
        "Cisco Firepower equipment:HDDFaultMonDef:dn managed
        object property"
    ::= { cfprEquipmentHDDFaultMonDefEntry 2 }

cfprEquipmentHDDFaultMonDefRn OBJECT-TYPE
    SYNTAX       SnmpAdminString
    MAX-ACCESS   read-only
    STATUS       current
    DESCRIPTION
        "Cisco Firepower equipment:HDDFaultMonDef:rn managed
        object property"
    ::= { cfprEquipmentHDDFaultMonDefEntry 3 }

cfprEquipmentHDDFaultMonDefControllerFwVersion OBJECT-TYPE
    SYNTAX       SnmpAdminString
    MAX-ACCESS   read-only
    STATUS       current
    DESCRIPTION
        "Cisco Firepower equipment:HDDFaultMonDef:ControllerFwVersion
        managed object property"
    ::= { cfprEquipmentHDDFaultMonDefEntry 4 }

cfprEquipmentHDDFaultMonDefControllerModel OBJECT-TYPE
    SYNTAX       SnmpAdminString
    MAX-ACCESS   read-only
    STATUS       current
    DESCRIPTION
        "Cisco Firepower equipment:HDDFaultMonDef:ControllerModel
        managed object property"
    ::= { cfprEquipmentHDDFaultMonDefEntry 5 }

cfprEquipmentHDDFaultMonDefHDDMonSupport OBJECT-TYPE
    SYNTAX       SnmpAdminString
    MAX-ACCESS   read-only
    STATUS       current
    DESCRIPTION
        "Cisco Firepower equipment:HDDFaultMonDef:HDDMonSupport
        managed object property"
    ::= { cfprEquipmentHDDFaultMonDefEntry 6 }

cfprEquipmentHDDFaultMonDefDescr OBJECT-TYPE
    SYNTAX       SnmpAdminString
    MAX-ACCESS   read-only
    STATUS       current
    DESCRIPTION
        "Cisco Firepower equipment:HDDFaultMonDef:descr
        managed object property"
    ::= { cfprEquipmentHDDFaultMonDefEntry 7 }

cfprEquipmentHDDFaultMonDefIntId OBJECT-TYPE
    SYNTAX       SnmpAdminString
    MAX-ACCESS   read-only
    STATUS       current
    DESCRIPTION
        "Cisco Firepower equipment:HDDFaultMonDef:intId
        managed object property"
    ::= { cfprEquipmentHDDFaultMonDefEntry 8 }

cfprEquipmentHDDFaultMonDefName OBJECT-TYPE
    SYNTAX       SnmpAdminString
    MAX-ACCESS   read-only
    STATUS       current
    DESCRIPTION
        "Cisco Firepower equipment:HDDFaultMonDef:name
        managed object property"
    ::= { cfprEquipmentHDDFaultMonDefEntry 9 }

cfprEquipmentHDDFaultMonDefPolicyLevel OBJECT-TYPE
    SYNTAX       Gauge32
    MAX-ACCESS   read-only
    STATUS       current
    DESCRIPTION
        "Cisco Firepower equipment:HDDFaultMonDef:policyLevel
        managed object property"
    ::= { cfprEquipmentHDDFaultMonDefEntry 10 }

cfprEquipmentHDDFaultMonDefPolicyOwner OBJECT-TYPE
    SYNTAX       CfprPolicyPolicyOwner
    MAX-ACCESS   read-only
    STATUS       current
    DESCRIPTION
        "Cisco Firepower equipment:HDDFaultMonDef:policyOwner
        managed object property"
    ::= { cfprEquipmentHDDFaultMonDefEntry 11 }

cfprEquipmentHealthLedTable OBJECT-TYPE
    SYNTAX           SEQUENCE OF CfprEquipmentHealthLedEntry
    MAX-ACCESS       not-accessible
    STATUS           current
    DESCRIPTION
        "Cisco Firepower equipment:HealthLed managed object table"
    ::= { cfprEquipmentObjects 60 }

cfprEquipmentHealthLedEntry OBJECT-TYPE
    SYNTAX           CfprEquipmentHealthLedEntry
    MAX-ACCESS       not-accessible
    STATUS           current
    DESCRIPTION
        "Entry for the cfprEquipmentHealthLedTable table."
    INDEX { cfprEquipmentHealthLedInstanceId }
    ::= { cfprEquipmentHealthLedTable 1 }

CfprEquipmentHealthLedEntry ::= SEQUENCE {
    cfprEquipmentHealthLedInstanceId                                 CfprManagedObjectId,
    cfprEquipmentHealthLedDn                                         CfprManagedObjectDn,
    cfprEquipmentHealthLedRn                                         SnmpAdminString,
    cfprEquipmentHealthLedColor                                      CfprEquipmentLedColor,
    cfprEquipmentHealthLedHealthLedState                             CfprEquipmentHealthLedState,
    cfprEquipmentHealthLedHealthLedStateQualifier                    SnmpAdminString,
    cfprEquipmentHealthLedId                                         Gauge32,
    cfprEquipmentHealthLedName                                       SnmpAdminString,
    cfprEquipmentHealthLedOperState                                  CfprEquipmentLedOperState
}

cfprEquipmentHealthLedInstanceId OBJECT-TYPE
    SYNTAX       CfprManagedObjectId
    MAX-ACCESS   not-accessible
    STATUS       current
    DESCRIPTION
        "Instance identifier of the managed object."
    ::= { cfprEquipmentHealthLedEntry 1 }

cfprEquipmentHealthLedDn OBJECT-TYPE
    SYNTAX       CfprManagedObjectDn
    MAX-ACCESS   read-only
    STATUS       current
    DESCRIPTION
        "Cisco Firepower equipment:HealthLed:dn managed object property"
    ::= { cfprEquipmentHealthLedEntry 2 }

cfprEquipmentHealthLedRn OBJECT-TYPE
    SYNTAX       SnmpAdminString
    MAX-ACCESS   read-only
    STATUS       current
    DESCRIPTION
        "Cisco Firepower equipment:HealthLed:rn managed object property"
    ::= { cfprEquipmentHealthLedEntry 3 }

cfprEquipmentHealthLedColor OBJECT-TYPE
    SYNTAX       CfprEquipmentLedColor
    MAX-ACCESS   read-only
    STATUS       current
    DESCRIPTION
        "Cisco Firepower equipment:HealthLed:color managed
        object property"
    ::= { cfprEquipmentHealthLedEntry 4 }

cfprEquipmentHealthLedHealthLedState OBJECT-TYPE
    SYNTAX       CfprEquipmentHealthLedState
    MAX-ACCESS   read-only
    STATUS       current
    DESCRIPTION
        "Cisco Firepower equipment:HealthLed:healthLedState
        managed object property"
    ::= { cfprEquipmentHealthLedEntry 5 }

cfprEquipmentHealthLedHealthLedStateQualifier OBJECT-TYPE
    SYNTAX       SnmpAdminString
    MAX-ACCESS   read-only
    STATUS       current
    DESCRIPTION
        "Cisco Firepower equipment:HealthLed:healthLedStateQualifier
        managed object property"
    ::= { cfprEquipmentHealthLedEntry 6 }

cfprEquipmentHealthLedId OBJECT-TYPE
    SYNTAX       Gauge32
    MAX-ACCESS   read-only
    STATUS       current
    DESCRIPTION
        "Cisco Firepower equipment:HealthLed:id managed object property"
    ::= { cfprEquipmentHealthLedEntry 7 }

cfprEquipmentHealthLedName OBJECT-TYPE
    SYNTAX       SnmpAdminString
    MAX-ACCESS   read-only
    STATUS       current
    DESCRIPTION
        "Cisco Firepower equipment:HealthLed:name managed object property"
    ::= { cfprEquipmentHealthLedEntry 8 }

cfprEquipmentHealthLedOperState OBJECT-TYPE
    SYNTAX       CfprEquipmentLedOperState
    MAX-ACCESS   read-only
    STATUS       current
    DESCRIPTION
        "Cisco Firepower equipment:HealthLed:operState
        managed object property"
    ::= { cfprEquipmentHealthLedEntry 9 }

cfprEquipmentHostIfCapProviderTable OBJECT-TYPE
    SYNTAX           SEQUENCE OF CfprEquipmentHostIfCapProviderEntry
    MAX-ACCESS       not-accessible
    STATUS           current
    DESCRIPTION
        "Cisco Firepower equipment:HostIfCapProvider managed object table"
    ::= { cfprEquipmentObjects 61 }

cfprEquipmentHostIfCapProviderEntry OBJECT-TYPE
    SYNTAX           CfprEquipmentHostIfCapProviderEntry
    MAX-ACCESS       not-accessible
    STATUS           current
    DESCRIPTION
        "Entry for the cfprEquipmentHostIfCapProviderTable table."
    INDEX { cfprEquipmentHostIfCapProviderInstanceId }
    ::= { cfprEquipmentHostIfCapProviderTable 1 }

CfprEquipmentHostIfCapProviderEntry ::= SEQUENCE {
    cfprEquipmentHostIfCapProviderInstanceId                         CfprManagedObjectId,
    cfprEquipmentHostIfCapProviderDn                                 CfprManagedObjectDn,
    cfprEquipmentHostIfCapProviderRn                                 SnmpAdminString,
    cfprEquipmentHostIfCapProviderDeleted                            TruthValue,
    cfprEquipmentHostIfCapProviderDeprecated                         TruthValue,
    cfprEquipmentHostIfCapProviderElementLoadFailures                Gauge32,
    cfprEquipmentHostIfCapProviderElementsLoaded                     Gauge32,
    cfprEquipmentHostIfCapProviderGencount                           Gauge32,
    cfprEquipmentHostIfCapProviderLoadErrors                         Gauge32,
    cfprEquipmentHostIfCapProviderLoadWarnings                       Gauge32,
    cfprEquipmentHostIfCapProviderMgmtPlaneVer                       SnmpAdminString,
    cfprEquipmentHostIfCapProviderModel                              SnmpAdminString,
    cfprEquipmentHostIfCapProviderPromCardType                       Gauge32,
    cfprEquipmentHostIfCapProviderRevision                           SnmpAdminString,
    cfprEquipmentHostIfCapProviderVendor                             SnmpAdminString
}

cfprEquipmentHostIfCapProviderInstanceId OBJECT-TYPE
    SYNTAX       CfprManagedObjectId
    MAX-ACCESS   not-accessible
    STATUS       current
    DESCRIPTION
        "Instance identifier of the managed object."
    ::= { cfprEquipmentHostIfCapProviderEntry 1 }

cfprEquipmentHostIfCapProviderDn OBJECT-TYPE
    SYNTAX       CfprManagedObjectDn
    MAX-ACCESS   read-only
    STATUS       current
    DESCRIPTION
        "Cisco Firepower equipment:HostIfCapProvider:dn
        managed object property"
    ::= { cfprEquipmentHostIfCapProviderEntry 2 }

cfprEquipmentHostIfCapProviderRn OBJECT-TYPE
    SYNTAX       SnmpAdminString
    MAX-ACCESS   read-only
    STATUS       current
    DESCRIPTION
        "Cisco Firepower equipment:HostIfCapProvider:rn
        managed object property"
    ::= { cfprEquipmentHostIfCapProviderEntry 3 }

cfprEquipmentHostIfCapProviderDeleted OBJECT-TYPE
    SYNTAX       TruthValue
    MAX-ACCESS   read-only
    STATUS       current
    DESCRIPTION
        "Cisco Firepower equipment:HostIfCapProvider:deleted
        managed object property"
    ::= { cfprEquipmentHostIfCapProviderEntry 4 }

cfprEquipmentHostIfCapProviderDeprecated OBJECT-TYPE
    SYNTAX       TruthValue
    MAX-ACCESS   read-only
    STATUS       current
    DESCRIPTION
        "Cisco Firepower equipment:HostIfCapProvider:deprecated
        managed object property"
    ::= { cfprEquipmentHostIfCapProviderEntry 5 }

cfprEquipmentHostIfCapProviderElementLoadFailures OBJECT-TYPE
    SYNTAX       Gauge32
    MAX-ACCESS   read-only
    STATUS       current
    DESCRIPTION
        "Cisco Firepower equipment:HostIfCapProvider:elementLoadFailures
        managed object property"
    ::= { cfprEquipmentHostIfCapProviderEntry 6 }

cfprEquipmentHostIfCapProviderElementsLoaded OBJECT-TYPE
    SYNTAX       Gauge32
    MAX-ACCESS   read-only
    STATUS       current
    DESCRIPTION
        "Cisco Firepower equipment:HostIfCapProvider:elementsLoaded
        managed object property"
    ::= { cfprEquipmentHostIfCapProviderEntry 7 }

cfprEquipmentHostIfCapProviderGencount OBJECT-TYPE
    SYNTAX       Gauge32
    MAX-ACCESS   read-only
    STATUS       current
    DESCRIPTION
        "Cisco Firepower equipment:HostIfCapProvider:gencount
        managed object property"
    ::= { cfprEquipmentHostIfCapProviderEntry 8 }

cfprEquipmentHostIfCapProviderLoadErrors OBJECT-TYPE
    SYNTAX       Gauge32
    MAX-ACCESS   read-only
    STATUS       current
    DESCRIPTION
        "Cisco Firepower equipment:HostIfCapProvider:loadErrors
        managed object property"
    ::= { cfprEquipmentHostIfCapProviderEntry 9 }

cfprEquipmentHostIfCapProviderLoadWarnings OBJECT-TYPE
    SYNTAX       Gauge32
    MAX-ACCESS   read-only
    STATUS       current
    DESCRIPTION
        "Cisco Firepower equipment:HostIfCapProvider:loadWarnings
        managed object property"
    ::= { cfprEquipmentHostIfCapProviderEntry 10 }

cfprEquipmentHostIfCapProviderMgmtPlaneVer OBJECT-TYPE
    SYNTAX       SnmpAdminString
    MAX-ACCESS   read-only
    STATUS       current
    DESCRIPTION
        "Cisco Firepower equipment:HostIfCapProvider:mgmtPlaneVer
        managed object property"
    ::= { cfprEquipmentHostIfCapProviderEntry 11 }

cfprEquipmentHostIfCapProviderModel OBJECT-TYPE
    SYNTAX       SnmpAdminString
    MAX-ACCESS   read-only
    STATUS       current
    DESCRIPTION
        "Cisco Firepower equipment:HostIfCapProvider:model
        managed object property"
    ::= { cfprEquipmentHostIfCapProviderEntry 12 }

cfprEquipmentHostIfCapProviderPromCardType OBJECT-TYPE
    SYNTAX       Gauge32
    MAX-ACCESS   read-only
    STATUS       current
    DESCRIPTION
        "Cisco Firepower equipment:HostIfCapProvider:promCardType
        managed object property"
    ::= { cfprEquipmentHostIfCapProviderEntry 13 }

cfprEquipmentHostIfCapProviderRevision OBJECT-TYPE
    SYNTAX       SnmpAdminString
    MAX-ACCESS   read-only
    STATUS       current
    DESCRIPTION
        "Cisco Firepower equipment:HostIfCapProvider:revision
        managed object property"
    ::= { cfprEquipmentHostIfCapProviderEntry 14 }

cfprEquipmentHostIfCapProviderVendor OBJECT-TYPE
    SYNTAX       SnmpAdminString
    MAX-ACCESS   read-only
    STATUS       current
    DESCRIPTION
        "Cisco Firepower equipment:HostIfCapProvider:vendor
        managed object property"
    ::= { cfprEquipmentHostIfCapProviderEntry 15 }

cfprEquipmentHwCapDerivativeProviderTable OBJECT-TYPE
    SYNTAX           SEQUENCE OF CfprEquipmentHwCapDerivativeProviderEntry
    MAX-ACCESS       not-accessible
    STATUS           current
    DESCRIPTION
        "Cisco Firepower equipment:HwCapDerivativeProvider
        managed object table"
    ::= { cfprEquipmentObjects 155 }

cfprEquipmentHwCapDerivativeProviderEntry OBJECT-TYPE
    SYNTAX           CfprEquipmentHwCapDerivativeProviderEntry
    MAX-ACCESS       not-accessible
    STATUS           current
    DESCRIPTION
        "Entry for the cfprEquipmentHwCapDerivativeProviderTable table."
    INDEX { cfprEquipmentHwCapDerivativeProviderInstanceId }
    ::= { cfprEquipmentHwCapDerivativeProviderTable 1 }

CfprEquipmentHwCapDerivativeProviderEntry ::= SEQUENCE {
    cfprEquipmentHwCapDerivativeProviderInstanceId                   CfprManagedObjectId,
    cfprEquipmentHwCapDerivativeProviderDn                           CfprManagedObjectDn,
    cfprEquipmentHwCapDerivativeProviderRn                           SnmpAdminString,
    cfprEquipmentHwCapDerivativeProviderDeleted                      TruthValue,
    cfprEquipmentHwCapDerivativeProviderDeprecated                   TruthValue,
    cfprEquipmentHwCapDerivativeProviderElementLoadFailures          Gauge32,
    cfprEquipmentHwCapDerivativeProviderElementsLoaded               Gauge32,
    cfprEquipmentHwCapDerivativeProviderGencount                     Gauge32,
    cfprEquipmentHwCapDerivativeProviderLoadErrors                   Gauge32,
    cfprEquipmentHwCapDerivativeProviderLoadWarnings                 Gauge32,
    cfprEquipmentHwCapDerivativeProviderMgmtPlaneVer                 SnmpAdminString,
    cfprEquipmentHwCapDerivativeProviderModel                        SnmpAdminString,
    cfprEquipmentHwCapDerivativeProviderRevision                     SnmpAdminString,
    cfprEquipmentHwCapDerivativeProviderVendor                       SnmpAdminString
}

cfprEquipmentHwCapDerivativeProviderInstanceId OBJECT-TYPE
    SYNTAX       CfprManagedObjectId
    MAX-ACCESS   not-accessible
    STATUS       current
    DESCRIPTION
        "Instance identifier of the managed object."
    ::= { cfprEquipmentHwCapDerivativeProviderEntry 1 }

cfprEquipmentHwCapDerivativeProviderDn OBJECT-TYPE
    SYNTAX       CfprManagedObjectDn
    MAX-ACCESS   read-only
    STATUS       current
    DESCRIPTION
        "Cisco Firepower equipment:HwCapDerivativeProvider:dn
        managed object property"
    ::= { cfprEquipmentHwCapDerivativeProviderEntry 2 }

cfprEquipmentHwCapDerivativeProviderRn OBJECT-TYPE
    SYNTAX       SnmpAdminString
    MAX-ACCESS   read-only
    STATUS       current
    DESCRIPTION
        "Cisco Firepower equipment:HwCapDerivativeProvider:rn
        managed object property"
    ::= { cfprEquipmentHwCapDerivativeProviderEntry 3 }

cfprEquipmentHwCapDerivativeProviderDeleted OBJECT-TYPE
    SYNTAX       TruthValue
    MAX-ACCESS   read-only
    STATUS       current
    DESCRIPTION
        "Cisco Firepower equipment:HwCapDerivativeProvider:deleted
        managed object property"
    ::= { cfprEquipmentHwCapDerivativeProviderEntry 4 }

cfprEquipmentHwCapDerivativeProviderDeprecated OBJECT-TYPE
    SYNTAX       TruthValue
    MAX-ACCESS   read-only
    STATUS       current
    DESCRIPTION
        "Cisco Firepower equipment:HwCapDerivativeProvider:deprecated
        managed object property"
    ::= { cfprEquipmentHwCapDerivativeProviderEntry 5 }

cfprEquipmentHwCapDerivativeProviderElementLoadFailures OBJECT-TYPE
    SYNTAX       Gauge32
    MAX-ACCESS   read-only
    STATUS       current
    DESCRIPTION
        "Cisco Firepower equipment:HwCapDerivativeProvider:elementLoadFail
        ures managed object property"
    ::= { cfprEquipmentHwCapDerivativeProviderEntry 6 }

cfprEquipmentHwCapDerivativeProviderElementsLoaded OBJECT-TYPE
    SYNTAX       Gauge32
    MAX-ACCESS   read-only
    STATUS       current
    DESCRIPTION
        "Cisco Firepower equipment:HwCapDerivativeProvider:elementsLoaded
        managed object property"
    ::= { cfprEquipmentHwCapDerivativeProviderEntry 7 }

cfprEquipmentHwCapDerivativeProviderGencount OBJECT-TYPE
    SYNTAX       Gauge32
    MAX-ACCESS   read-only
    STATUS       current
    DESCRIPTION
        "Cisco Firepower equipment:HwCapDerivativeProvider:gencount
        managed object property"
    ::= { cfprEquipmentHwCapDerivativeProviderEntry 8 }

cfprEquipmentHwCapDerivativeProviderLoadErrors OBJECT-TYPE
    SYNTAX       Gauge32
    MAX-ACCESS   read-only
    STATUS       current
    DESCRIPTION
        "Cisco Firepower equipment:HwCapDerivativeProvider:loadErrors
        managed object property"
    ::= { cfprEquipmentHwCapDerivativeProviderEntry 9 }

cfprEquipmentHwCapDerivativeProviderLoadWarnings OBJECT-TYPE
    SYNTAX       Gauge32
    MAX-ACCESS   read-only
    STATUS       current
    DESCRIPTION
        "Cisco Firepower equipment:HwCapDerivativeProvider:loadWarnings
        managed object property"
    ::= { cfprEquipmentHwCapDerivativeProviderEntry 10 }

cfprEquipmentHwCapDerivativeProviderMgmtPlaneVer OBJECT-TYPE
    SYNTAX       SnmpAdminString
    MAX-ACCESS   read-only
    STATUS       current
    DESCRIPTION
        "Cisco Firepower equipment:HwCapDerivativeProvider:mgmtPlaneVer
        managed object property"
    ::= { cfprEquipmentHwCapDerivativeProviderEntry 11 }

cfprEquipmentHwCapDerivativeProviderModel OBJECT-TYPE
    SYNTAX       SnmpAdminString
    MAX-ACCESS   read-only
    STATUS       current
    DESCRIPTION
        "Cisco Firepower equipment:HwCapDerivativeProvider:model
        managed object property"
    ::= { cfprEquipmentHwCapDerivativeProviderEntry 12 }

cfprEquipmentHwCapDerivativeProviderRevision OBJECT-TYPE
    SYNTAX       SnmpAdminString
    MAX-ACCESS   read-only
    STATUS       current
    DESCRIPTION
        "Cisco Firepower equipment:HwCapDerivativeProvider:revision
        managed object property"
    ::= { cfprEquipmentHwCapDerivativeProviderEntry 13 }

cfprEquipmentHwCapDerivativeProviderVendor OBJECT-TYPE
    SYNTAX       SnmpAdminString
    MAX-ACCESS   read-only
    STATUS       current
    DESCRIPTION
        "Cisco Firepower equipment:HwCapDerivativeProvider:vendor
        managed object property"
    ::= { cfprEquipmentHwCapDerivativeProviderEntry 14 }

cfprEquipmentIOCardTable OBJECT-TYPE
    SYNTAX           SEQUENCE OF CfprEquipmentIOCardEntry
    MAX-ACCESS       not-accessible
    STATUS           current
    DESCRIPTION
        "Cisco Firepower equipment:IOCard managed object table"
    ::= { cfprEquipmentObjects 62 }

cfprEquipmentIOCardEntry OBJECT-TYPE
    SYNTAX           CfprEquipmentIOCardEntry
    MAX-ACCESS       not-accessible
    STATUS           current
    DESCRIPTION
        "Entry for the cfprEquipmentIOCardTable table."
    INDEX { cfprEquipmentIOCardInstanceId }
    ::= { cfprEquipmentIOCardTable 1 }

CfprEquipmentIOCardEntry ::= SEQUENCE {
    cfprEquipmentIOCardInstanceId                                    CfprManagedObjectId,
    cfprEquipmentIOCardDn                                            CfprManagedObjectDn,
    cfprEquipmentIOCardRn                                            SnmpAdminString,
    cfprEquipmentIOCardAdminPowerState                               CfprEquipmentAdminPowerState,
    cfprEquipmentIOCardBaseAddr                                      InetAddressIPv4,
    cfprEquipmentIOCardChassisId                                     Gauge32,
    cfprEquipmentIOCardConfigState                                   CfprEquipmentChassisConfigState,
    cfprEquipmentIOCardDiscovery                                     CfprEquipmentDiscoveryState,
    cfprEquipmentIOCardFeOfflineTs                                   Unsigned64,
    cfprEquipmentIOCardFeReadyTs                                     Unsigned64,
    cfprEquipmentIOCardFltAggr                                       Unsigned64,
    cfprEquipmentIOCardFsmDescr                                      SnmpAdminString,
    cfprEquipmentIOCardFsmFlags                                      SnmpAdminString,
    cfprEquipmentIOCardFsmPrev                                       SnmpAdminString,
    cfprEquipmentIOCardFsmProgr                                      Gauge32,
    cfprEquipmentIOCardFsmRmtInvErrCode                              Gauge32,
    cfprEquipmentIOCardFsmRmtInvErrDescr                             SnmpAdminString,
    cfprEquipmentIOCardFsmRmtInvRslt                                 CfprConditionRemoteInvRslt,
    cfprEquipmentIOCardFsmStageDescr                                 SnmpAdminString,
    cfprEquipmentIOCardFsmStamp                                      DateAndTime,
    cfprEquipmentIOCardFsmStatus                                     SnmpAdminString,
    cfprEquipmentIOCardFsmTry                                        Gauge32,
    cfprEquipmentIOCardId                                            CfprEquipmentIOCardId,
    cfprEquipmentIOCardLcName                                        SnmpAdminString,
    cfprEquipmentIOCardLcTs                                          DateAndTime,
    cfprEquipmentIOCardMfgTime                                       DateAndTime,
    cfprEquipmentIOCardModel                                         SnmpAdminString,
    cfprEquipmentIOCardOperQualifier                                 CfprEquipmentIOCardIssues,
    cfprEquipmentIOCardOperQualifierReason                           SnmpAdminString,
    cfprEquipmentIOCardOperState                                     CfprEquipmentOperability,
    cfprEquipmentIOCardOperability                                   CfprEquipmentOperability,
    cfprEquipmentIOCardPartNumber                                    SnmpAdminString,
    cfprEquipmentIOCardPeerCommStatus                                CfprEquipmentCommStatus,
    cfprEquipmentIOCardPeerDn                                        SnmpAdminString,
    cfprEquipmentIOCardPerf                                          CfprEquipmentSensorThresholdStatus,
    cfprEquipmentIOCardPower                                         CfprEquipmentPowerState,
    cfprEquipmentIOCardPresence                                      CfprEquipmentPresence,
    cfprEquipmentIOCardProcessorThermalState                         CfprEquipmentSensorThresholdStatus,
    cfprEquipmentIOCardRevision                                      SnmpAdminString,
    cfprEquipmentIOCardSerial                                        SnmpAdminString,
    cfprEquipmentIOCardSide                                          CfprNetworkSide,
    cfprEquipmentIOCardSwitchId                                      CfprNetworkSwitchId,
    cfprEquipmentIOCardThermal                                       CfprEquipmentSensorThresholdStatus,
    cfprEquipmentIOCardUpgradeStatus                                 CfprMgmtUpgradeStatus,
    cfprEquipmentIOCardUsrLbl                                        SnmpAdminString,
    cfprEquipmentIOCardVendor                                        SnmpAdminString,
    cfprEquipmentIOCardVid                                           SnmpAdminString,
    cfprEquipmentIOCardVoltage                                       CfprEquipmentSensorThresholdStatus
}

cfprEquipmentIOCardInstanceId OBJECT-TYPE
    SYNTAX       CfprManagedObjectId
    MAX-ACCESS   not-accessible
    STATUS       current
    DESCRIPTION
        "Instance identifier of the managed object."
    ::= { cfprEquipmentIOCardEntry 1 }

cfprEquipmentIOCardDn OBJECT-TYPE
    SYNTAX       CfprManagedObjectDn
    MAX-ACCESS   read-only
    STATUS       current
    DESCRIPTION
        "Cisco Firepower equipment:IOCard:dn managed object property"
    ::= { cfprEquipmentIOCardEntry 2 }

cfprEquipmentIOCardRn OBJECT-TYPE
    SYNTAX       SnmpAdminString
    MAX-ACCESS   read-only
    STATUS       current
    DESCRIPTION
        "Cisco Firepower equipment:IOCard:rn managed object property"
    ::= { cfprEquipmentIOCardEntry 3 }

cfprEquipmentIOCardAdminPowerState OBJECT-TYPE
    SYNTAX       CfprEquipmentAdminPowerState
    MAX-ACCESS   read-only
    STATUS       current
    DESCRIPTION
        "Cisco Firepower equipment:IOCard:adminPowerState
        managed object property"
    ::= { cfprEquipmentIOCardEntry 4 }

cfprEquipmentIOCardBaseAddr OBJECT-TYPE
    SYNTAX       InetAddressIPv4
    MAX-ACCESS   read-only
    STATUS       current
    DESCRIPTION
        "Cisco Firepower equipment:IOCard:baseAddr managed
        object property"
    ::= { cfprEquipmentIOCardEntry 5 }

cfprEquipmentIOCardChassisId OBJECT-TYPE
    SYNTAX       Gauge32
    MAX-ACCESS   read-only
    STATUS       current
    DESCRIPTION
        "Cisco Firepower equipment:IOCard:chassisId managed
        object property"
    ::= { cfprEquipmentIOCardEntry 6 }

cfprEquipmentIOCardConfigState OBJECT-TYPE
    SYNTAX       CfprEquipmentChassisConfigState
    MAX-ACCESS   read-only
    STATUS       current
    DESCRIPTION
        "Cisco Firepower equipment:IOCard:configState managed
        object property"
    ::= { cfprEquipmentIOCardEntry 7 }

cfprEquipmentIOCardDiscovery OBJECT-TYPE
    SYNTAX       CfprEquipmentDiscoveryState
    MAX-ACCESS   read-only
    STATUS       current
    DESCRIPTION
        "Cisco Firepower equipment:IOCard:discovery managed
        object property"
    ::= { cfprEquipmentIOCardEntry 8 }

cfprEquipmentIOCardFeOfflineTs OBJECT-TYPE
    SYNTAX       Unsigned64
    MAX-ACCESS   read-only
    STATUS       current
    DESCRIPTION
        "Cisco Firepower equipment:IOCard:feOfflineTs managed
        object property"
    ::= { cfprEquipmentIOCardEntry 9 }

cfprEquipmentIOCardFeReadyTs OBJECT-TYPE
    SYNTAX       Unsigned64
    MAX-ACCESS   read-only
    STATUS       current
    DESCRIPTION
        "Cisco Firepower equipment:IOCard:feReadyTs managed
        object property"
    ::= { cfprEquipmentIOCardEntry 10 }

cfprEquipmentIOCardFltAggr OBJECT-TYPE
    SYNTAX       Unsigned64
    MAX-ACCESS   read-only
    STATUS       current
    DESCRIPTION
        "Cisco Firepower equipment:IOCard:fltAggr managed object property"
    ::= { cfprEquipmentIOCardEntry 11 }

cfprEquipmentIOCardFsmDescr OBJECT-TYPE
    SYNTAX       SnmpAdminString
    MAX-ACCESS   read-only
    STATUS       current
    DESCRIPTION
        "Cisco Firepower equipment:IOCard:fsmDescr managed
        object property"
    ::= { cfprEquipmentIOCardEntry 12 }

cfprEquipmentIOCardFsmFlags OBJECT-TYPE
    SYNTAX       SnmpAdminString
    MAX-ACCESS   read-only
    STATUS       current
    DESCRIPTION
        "Cisco Firepower equipment:IOCard:fsmFlags managed
        object property"
    ::= { cfprEquipmentIOCardEntry 13 }

cfprEquipmentIOCardFsmPrev OBJECT-TYPE
    SYNTAX       SnmpAdminString
    MAX-ACCESS   read-only
    STATUS       current
    DESCRIPTION
        "Cisco Firepower equipment:IOCard:fsmPrev managed object property"
    ::= { cfprEquipmentIOCardEntry 14 }

cfprEquipmentIOCardFsmProgr OBJECT-TYPE
    SYNTAX       Gauge32
    MAX-ACCESS   read-only
    STATUS       current
    DESCRIPTION
        "Cisco Firepower equipment:IOCard:fsmProgr managed
        object property"
    ::= { cfprEquipmentIOCardEntry 15 }

cfprEquipmentIOCardFsmRmtInvErrCode OBJECT-TYPE
    SYNTAX       Gauge32
    MAX-ACCESS   read-only
    STATUS       current
    DESCRIPTION
        "Cisco Firepower equipment:IOCard:fsmRmtInvErrCode
        managed object property"
    ::= { cfprEquipmentIOCardEntry 16 }

cfprEquipmentIOCardFsmRmtInvErrDescr OBJECT-TYPE
    SYNTAX       SnmpAdminString
    MAX-ACCESS   read-only
    STATUS       current
    DESCRIPTION
        "Cisco Firepower equipment:IOCard:fsmRmtInvErrDescr
        managed object property"
    ::= { cfprEquipmentIOCardEntry 17 }

cfprEquipmentIOCardFsmRmtInvRslt OBJECT-TYPE
    SYNTAX       CfprConditionRemoteInvRslt
    MAX-ACCESS   read-only
    STATUS       current
    DESCRIPTION
        "Cisco Firepower equipment:IOCard:fsmRmtInvRslt
        managed object property"
    ::= { cfprEquipmentIOCardEntry 18 }

cfprEquipmentIOCardFsmStageDescr OBJECT-TYPE
    SYNTAX       SnmpAdminString
    MAX-ACCESS   read-only
    STATUS       current
    DESCRIPTION
        "Cisco Firepower equipment:IOCard:fsmStageDescr
        managed object property"
    ::= { cfprEquipmentIOCardEntry 19 }

cfprEquipmentIOCardFsmStamp OBJECT-TYPE
    SYNTAX       DateAndTime
    MAX-ACCESS   read-only
    STATUS       current
    DESCRIPTION
        "Cisco Firepower equipment:IOCard:fsmStamp managed
        object property"
    ::= { cfprEquipmentIOCardEntry 20 }

cfprEquipmentIOCardFsmStatus OBJECT-TYPE
    SYNTAX       SnmpAdminString
    MAX-ACCESS   read-only
    STATUS       current
    DESCRIPTION
        "Cisco Firepower equipment:IOCard:fsmStatus managed
        object property"
    ::= { cfprEquipmentIOCardEntry 21 }

cfprEquipmentIOCardFsmTry OBJECT-TYPE
    SYNTAX       Gauge32
    MAX-ACCESS   read-only
    STATUS       current
    DESCRIPTION
        "Cisco Firepower equipment:IOCard:fsmTry managed object property"
    ::= { cfprEquipmentIOCardEntry 22 }

cfprEquipmentIOCardId OBJECT-TYPE
    SYNTAX       CfprEquipmentIOCardId
    MAX-ACCESS   read-only
    STATUS       current
    DESCRIPTION
        "Cisco Firepower equipment:IOCard:id managed object property"
    ::= { cfprEquipmentIOCardEntry 23 }

cfprEquipmentIOCardLcName OBJECT-TYPE
    SYNTAX       SnmpAdminString
    MAX-ACCESS   read-only
    STATUS       current
    DESCRIPTION
        "Cisco Firepower equipment:IOCard:lcName managed object property"
    ::= { cfprEquipmentIOCardEntry 24 }

cfprEquipmentIOCardLcTs OBJECT-TYPE
    SYNTAX       DateAndTime
    MAX-ACCESS   read-only
    STATUS       current
    DESCRIPTION
        "Cisco Firepower equipment:IOCard:lcTs managed object property"
    ::= { cfprEquipmentIOCardEntry 25 }

cfprEquipmentIOCardMfgTime OBJECT-TYPE
    SYNTAX       DateAndTime
    MAX-ACCESS   read-only
    STATUS       current
    DESCRIPTION
        "Cisco Firepower equipment:IOCard:mfgTime managed object property"
    ::= { cfprEquipmentIOCardEntry 26 }

cfprEquipmentIOCardModel OBJECT-TYPE
    SYNTAX       SnmpAdminString
    MAX-ACCESS   read-only
    STATUS       current
    DESCRIPTION
        "Cisco Firepower equipment:IOCard:model managed object property"
    ::= { cfprEquipmentIOCardEntry 27 }

cfprEquipmentIOCardOperQualifier OBJECT-TYPE
    SYNTAX       CfprEquipmentIOCardIssues
    MAX-ACCESS   read-only
    STATUS       current
    DESCRIPTION
        "Cisco Firepower equipment:IOCard:operQualifier
        managed object property"
    ::= { cfprEquipmentIOCardEntry 28 }

cfprEquipmentIOCardOperQualifierReason OBJECT-TYPE
    SYNTAX       SnmpAdminString
    MAX-ACCESS   read-only
    STATUS       current
    DESCRIPTION
        "Cisco Firepower equipment:IOCard:operQualifierReason
        managed object property"
    ::= { cfprEquipmentIOCardEntry 29 }

cfprEquipmentIOCardOperState OBJECT-TYPE
    SYNTAX       CfprEquipmentOperability
    MAX-ACCESS   read-only
    STATUS       current
    DESCRIPTION
        "Cisco Firepower equipment:IOCard:operState managed
        object property"
    ::= { cfprEquipmentIOCardEntry 30 }

cfprEquipmentIOCardOperability OBJECT-TYPE
    SYNTAX       CfprEquipmentOperability
    MAX-ACCESS   read-only
    STATUS       current
    DESCRIPTION
        "Cisco Firepower equipment:IOCard:operability managed
        object property"
    ::= { cfprEquipmentIOCardEntry 31 }

cfprEquipmentIOCardPartNumber OBJECT-TYPE
    SYNTAX       SnmpAdminString
    MAX-ACCESS   read-only
    STATUS       current
    DESCRIPTION
        "Cisco Firepower equipment:IOCard:partNumber managed
        object property"
    ::= { cfprEquipmentIOCardEntry 32 }

cfprEquipmentIOCardPeerCommStatus OBJECT-TYPE
    SYNTAX       CfprEquipmentCommStatus
    MAX-ACCESS   read-only
    STATUS       current
    DESCRIPTION
        "Cisco Firepower equipment:IOCard:peerCommStatus
        managed object property"
    ::= { cfprEquipmentIOCardEntry 33 }

cfprEquipmentIOCardPeerDn OBJECT-TYPE
    SYNTAX       SnmpAdminString
    MAX-ACCESS   read-only
    STATUS       current
    DESCRIPTION
        "Cisco Firepower equipment:IOCard:peerDn managed object property"
    ::= { cfprEquipmentIOCardEntry 34 }

cfprEquipmentIOCardPerf OBJECT-TYPE
    SYNTAX       CfprEquipmentSensorThresholdStatus
    MAX-ACCESS   read-only
    STATUS       current
    DESCRIPTION
        "Cisco Firepower equipment:IOCard:perf managed object property"
    ::= { cfprEquipmentIOCardEntry 35 }

cfprEquipmentIOCardPower OBJECT-TYPE
    SYNTAX       CfprEquipmentPowerState
    MAX-ACCESS   read-only
    STATUS       current
    DESCRIPTION
        "Cisco Firepower equipment:IOCard:power managed object property"
    ::= { cfprEquipmentIOCardEntry 36 }

cfprEquipmentIOCardPresence OBJECT-TYPE
    SYNTAX       CfprEquipmentPresence
    MAX-ACCESS   read-only
    STATUS       current
    DESCRIPTION
        "Cisco Firepower equipment:IOCard:presence managed
        object property"
    ::= { cfprEquipmentIOCardEntry 37 }

cfprEquipmentIOCardProcessorThermalState OBJECT-TYPE
    SYNTAX       CfprEquipmentSensorThresholdStatus
    MAX-ACCESS   read-only
    STATUS       current
    DESCRIPTION
        "Cisco Firepower equipment:IOCard:processorThermalState
        managed object property"
    ::= { cfprEquipmentIOCardEntry 38 }

cfprEquipmentIOCardRevision OBJECT-TYPE
    SYNTAX       SnmpAdminString
    MAX-ACCESS   read-only
    STATUS       current
    DESCRIPTION
        "Cisco Firepower equipment:IOCard:revision managed
        object property"
    ::= { cfprEquipmentIOCardEntry 39 }

cfprEquipmentIOCardSerial OBJECT-TYPE
    SYNTAX       SnmpAdminString
    MAX-ACCESS   read-only
    STATUS       current
    DESCRIPTION
        "Cisco Firepower equipment:IOCard:serial managed object property"
    ::= { cfprEquipmentIOCardEntry 40 }

cfprEquipmentIOCardSide OBJECT-TYPE
    SYNTAX       CfprNetworkSide
    MAX-ACCESS   read-only
    STATUS       current
    DESCRIPTION
        "Cisco Firepower equipment:IOCard:side managed object property"
    ::= { cfprEquipmentIOCardEntry 41 }

cfprEquipmentIOCardSwitchId OBJECT-TYPE
    SYNTAX       CfprNetworkSwitchId
    MAX-ACCESS   read-only
    STATUS       current
    DESCRIPTION
        "Cisco Firepower equipment:IOCard:switchId managed
        object property"
    ::= { cfprEquipmentIOCardEntry 42 }

cfprEquipmentIOCardThermal OBJECT-TYPE
    SYNTAX       CfprEquipmentSensorThresholdStatus
    MAX-ACCESS   read-only
    STATUS       current
    DESCRIPTION
        "Cisco Firepower equipment:IOCard:thermal managed object property"
    ::= { cfprEquipmentIOCardEntry 43 }

cfprEquipmentIOCardUpgradeStatus OBJECT-TYPE
    SYNTAX       CfprMgmtUpgradeStatus
    MAX-ACCESS   read-only
    STATUS       current
    DESCRIPTION
        "Cisco Firepower equipment:IOCard:upgradeStatus
        managed object property"
    ::= { cfprEquipmentIOCardEntry 44 }

cfprEquipmentIOCardUsrLbl OBJECT-TYPE
    SYNTAX       SnmpAdminString
    MAX-ACCESS   read-only
    STATUS       current
    DESCRIPTION
        "Cisco Firepower equipment:IOCard:usrLbl managed object property"
    ::= { cfprEquipmentIOCardEntry 45 }

cfprEquipmentIOCardVendor OBJECT-TYPE
    SYNTAX       SnmpAdminString
    MAX-ACCESS   read-only
    STATUS       current
    DESCRIPTION
        "Cisco Firepower equipment:IOCard:vendor managed object property"
    ::= { cfprEquipmentIOCardEntry 46 }

cfprEquipmentIOCardVid OBJECT-TYPE
    SYNTAX       SnmpAdminString
    MAX-ACCESS   read-only
    STATUS       current
    DESCRIPTION
        "Cisco Firepower equipment:IOCard:vid managed object property"
    ::= { cfprEquipmentIOCardEntry 47 }

cfprEquipmentIOCardVoltage OBJECT-TYPE
    SYNTAX       CfprEquipmentSensorThresholdStatus
    MAX-ACCESS   read-only
    STATUS       current
    DESCRIPTION
        "Cisco Firepower equipment:IOCard:voltage managed object property"
    ::= { cfprEquipmentIOCardEntry 48 }

cfprEquipmentIOCardBaseFsmTable OBJECT-TYPE
    SYNTAX           SEQUENCE OF CfprEquipmentIOCardBaseFsmEntry
    MAX-ACCESS       not-accessible
    STATUS           current
    DESCRIPTION
        "Cisco Firepower equipment:IOCardBaseFsm managed object table"
    ::= { cfprEquipmentObjects 63 }

cfprEquipmentIOCardBaseFsmEntry OBJECT-TYPE
    SYNTAX           CfprEquipmentIOCardBaseFsmEntry
    MAX-ACCESS       not-accessible
    STATUS           current
    DESCRIPTION
        "Entry for the cfprEquipmentIOCardBaseFsmTable table."
    INDEX { cfprEquipmentIOCardBaseFsmInstanceId }
    ::= { cfprEquipmentIOCardBaseFsmTable 1 }

CfprEquipmentIOCardBaseFsmEntry ::= SEQUENCE {
    cfprEquipmentIOCardBaseFsmInstanceId                             CfprManagedObjectId,
    cfprEquipmentIOCardBaseFsmDn                                     CfprManagedObjectDn,
    cfprEquipmentIOCardBaseFsmRn                                     SnmpAdminString,
    cfprEquipmentIOCardBaseFsmCompletionTime                         DateAndTime,
    cfprEquipmentIOCardBaseFsmCurrentFsm                             CfprEquipmentIOCardBaseFsmCurrentFsm,
    cfprEquipmentIOCardBaseFsmDescr                                  SnmpAdminString,
    cfprEquipmentIOCardBaseFsmFsmStatus                              CfprFsmFsmStageStatus,
    cfprEquipmentIOCardBaseFsmProgress                               Gauge32,
    cfprEquipmentIOCardBaseFsmRmtErrCode                             Gauge32,
    cfprEquipmentIOCardBaseFsmRmtErrDescr                            SnmpAdminString,
    cfprEquipmentIOCardBaseFsmRmtRslt                                CfprConditionRemoteInvRslt
}

cfprEquipmentIOCardBaseFsmInstanceId OBJECT-TYPE
    SYNTAX       CfprManagedObjectId
    MAX-ACCESS   not-accessible
    STATUS       current
    DESCRIPTION
        "Instance identifier of the managed object."
    ::= { cfprEquipmentIOCardBaseFsmEntry 1 }

cfprEquipmentIOCardBaseFsmDn OBJECT-TYPE
    SYNTAX       CfprManagedObjectDn
    MAX-ACCESS   read-only
    STATUS       current
    DESCRIPTION
        "Cisco Firepower equipment:IOCardBaseFsm:dn managed
        object property"
    ::= { cfprEquipmentIOCardBaseFsmEntry 2 }

cfprEquipmentIOCardBaseFsmRn OBJECT-TYPE
    SYNTAX       SnmpAdminString
    MAX-ACCESS   read-only
    STATUS       current
    DESCRIPTION
        "Cisco Firepower equipment:IOCardBaseFsm:rn managed
        object property"
    ::= { cfprEquipmentIOCardBaseFsmEntry 3 }

cfprEquipmentIOCardBaseFsmCompletionTime OBJECT-TYPE
    SYNTAX       DateAndTime
    MAX-ACCESS   read-only
    STATUS       current
    DESCRIPTION
        "Cisco Firepower equipment:IOCardBaseFsm:completionTime
        managed object property"
    ::= { cfprEquipmentIOCardBaseFsmEntry 4 }

cfprEquipmentIOCardBaseFsmCurrentFsm OBJECT-TYPE
    SYNTAX       CfprEquipmentIOCardBaseFsmCurrentFsm
    MAX-ACCESS   read-only
    STATUS       current
    DESCRIPTION
        "Cisco Firepower equipment:IOCardBaseFsm:currentFsm
        managed object property"
    ::= { cfprEquipmentIOCardBaseFsmEntry 5 }

cfprEquipmentIOCardBaseFsmDescr OBJECT-TYPE
    SYNTAX       SnmpAdminString
    MAX-ACCESS   read-only
    STATUS       current
    DESCRIPTION
        "Cisco Firepower equipment:IOCardBaseFsm:descr
        managed object property"
    ::= { cfprEquipmentIOCardBaseFsmEntry 6 }

cfprEquipmentIOCardBaseFsmFsmStatus OBJECT-TYPE
    SYNTAX       CfprFsmFsmStageStatus
    MAX-ACCESS   read-only
    STATUS       current
    DESCRIPTION
        "Cisco Firepower equipment:IOCardBaseFsm:fsmStatus
        managed object property"
    ::= { cfprEquipmentIOCardBaseFsmEntry 7 }

cfprEquipmentIOCardBaseFsmProgress OBJECT-TYPE
    SYNTAX       Gauge32
    MAX-ACCESS   read-only
    STATUS       current
    DESCRIPTION
        "Cisco Firepower equipment:IOCardBaseFsm:progress
        managed object property"
    ::= { cfprEquipmentIOCardBaseFsmEntry 8 }

cfprEquipmentIOCardBaseFsmRmtErrCode OBJECT-TYPE
    SYNTAX       Gauge32
    MAX-ACCESS   read-only
    STATUS       current
    DESCRIPTION
        "Cisco Firepower equipment:IOCardBaseFsm:rmtErrCode
        managed object property"
    ::= { cfprEquipmentIOCardBaseFsmEntry 9 }

cfprEquipmentIOCardBaseFsmRmtErrDescr OBJECT-TYPE
    SYNTAX       SnmpAdminString
    MAX-ACCESS   read-only
    STATUS       current
    DESCRIPTION
        "Cisco Firepower equipment:IOCardBaseFsm:rmtErrDescr
        managed object property"
    ::= { cfprEquipmentIOCardBaseFsmEntry 10 }

cfprEquipmentIOCardBaseFsmRmtRslt OBJECT-TYPE
    SYNTAX       CfprConditionRemoteInvRslt
    MAX-ACCESS   read-only
    STATUS       current
    DESCRIPTION
        "Cisco Firepower equipment:IOCardBaseFsm:rmtRslt
        managed object property"
    ::= { cfprEquipmentIOCardBaseFsmEntry 11 }

cfprEquipmentIOCardBaseFsmStageTable OBJECT-TYPE
    SYNTAX           SEQUENCE OF CfprEquipmentIOCardBaseFsmStageEntry
    MAX-ACCESS       not-accessible
    STATUS           current
    DESCRIPTION
        "Cisco Firepower equipment:IOCardBaseFsmStage managed
        object table"
    ::= { cfprEquipmentObjects 64 }

cfprEquipmentIOCardBaseFsmStageEntry OBJECT-TYPE
    SYNTAX           CfprEquipmentIOCardBaseFsmStageEntry
    MAX-ACCESS       not-accessible
    STATUS           current
    DESCRIPTION
        "Entry for the cfprEquipmentIOCardBaseFsmStageTable table."
    INDEX { cfprEquipmentIOCardBaseFsmStageInstanceId }
    ::= { cfprEquipmentIOCardBaseFsmStageTable 1 }

CfprEquipmentIOCardBaseFsmStageEntry ::= SEQUENCE {
    cfprEquipmentIOCardBaseFsmStageInstanceId                        CfprManagedObjectId,
    cfprEquipmentIOCardBaseFsmStageDn                                CfprManagedObjectDn,
    cfprEquipmentIOCardBaseFsmStageRn                                SnmpAdminString,
    cfprEquipmentIOCardBaseFsmStageDescr                             SnmpAdminString,
    cfprEquipmentIOCardBaseFsmStageLastUpdateTime                    DateAndTime,
    cfprEquipmentIOCardBaseFsmStageName                              CfprEquipmentIOCardBaseFsmStageName,
    cfprEquipmentIOCardBaseFsmStageOrder                             Gauge32,
    cfprEquipmentIOCardBaseFsmStageRetry                             Gauge32,
    cfprEquipmentIOCardBaseFsmStageStageStatus                       CfprFsmFsmStageStatus
}

cfprEquipmentIOCardBaseFsmStageInstanceId OBJECT-TYPE
    SYNTAX       CfprManagedObjectId
    MAX-ACCESS   not-accessible
    STATUS       current
    DESCRIPTION
        "Instance identifier of the managed object."
    ::= { cfprEquipmentIOCardBaseFsmStageEntry 1 }

cfprEquipmentIOCardBaseFsmStageDn OBJECT-TYPE
    SYNTAX       CfprManagedObjectDn
    MAX-ACCESS   read-only
    STATUS       current
    DESCRIPTION
        "Cisco Firepower equipment:IOCardBaseFsmStage:dn
        managed object property"
    ::= { cfprEquipmentIOCardBaseFsmStageEntry 2 }

cfprEquipmentIOCardBaseFsmStageRn OBJECT-TYPE
    SYNTAX       SnmpAdminString
    MAX-ACCESS   read-only
    STATUS       current
    DESCRIPTION
        "Cisco Firepower equipment:IOCardBaseFsmStage:rn
        managed object property"
    ::= { cfprEquipmentIOCardBaseFsmStageEntry 3 }

cfprEquipmentIOCardBaseFsmStageDescr OBJECT-TYPE
    SYNTAX       SnmpAdminString
    MAX-ACCESS   read-only
    STATUS       current
    DESCRIPTION
        "Cisco Firepower equipment:IOCardBaseFsmStage:descr
        managed object property"
    ::= { cfprEquipmentIOCardBaseFsmStageEntry 4 }

cfprEquipmentIOCardBaseFsmStageLastUpdateTime OBJECT-TYPE
    SYNTAX       DateAndTime
    MAX-ACCESS   read-only
    STATUS       current
    DESCRIPTION
        "Cisco Firepower equipment:IOCardBaseFsmStage:lastUpdateTime
        managed object property"
    ::= { cfprEquipmentIOCardBaseFsmStageEntry 5 }

cfprEquipmentIOCardBaseFsmStageName OBJECT-TYPE
    SYNTAX       CfprEquipmentIOCardBaseFsmStageName
    MAX-ACCESS   read-only
    STATUS       current
    DESCRIPTION
        "Cisco Firepower equipment:IOCardBaseFsmStage:name
        managed object property"
    ::= { cfprEquipmentIOCardBaseFsmStageEntry 6 }

cfprEquipmentIOCardBaseFsmStageOrder OBJECT-TYPE
    SYNTAX       Gauge32
    MAX-ACCESS   read-only
    STATUS       current
    DESCRIPTION
        "Cisco Firepower equipment:IOCardBaseFsmStage:order
        managed object property"
    ::= { cfprEquipmentIOCardBaseFsmStageEntry 7 }

cfprEquipmentIOCardBaseFsmStageRetry OBJECT-TYPE
    SYNTAX       Gauge32
    MAX-ACCESS   read-only
    STATUS       current
    DESCRIPTION
        "Cisco Firepower equipment:IOCardBaseFsmStage:retry
        managed object property"
    ::= { cfprEquipmentIOCardBaseFsmStageEntry 8 }

cfprEquipmentIOCardBaseFsmStageStageStatus OBJECT-TYPE
    SYNTAX       CfprFsmFsmStageStatus
    MAX-ACCESS   read-only
    STATUS       current
    DESCRIPTION
        "Cisco Firepower equipment:IOCardBaseFsmStage:stageStatus
        managed object property"
    ::= { cfprEquipmentIOCardBaseFsmStageEntry 9 }

cfprEquipmentIOCardBaseFsmTaskTable OBJECT-TYPE
    SYNTAX           SEQUENCE OF CfprEquipmentIOCardBaseFsmTaskEntry
    MAX-ACCESS       not-accessible
    STATUS           current
    DESCRIPTION
        "Cisco Firepower equipment:IOCardBaseFsmTask managed object table"
    ::= { cfprEquipmentObjects 65 }

cfprEquipmentIOCardBaseFsmTaskEntry OBJECT-TYPE
    SYNTAX           CfprEquipmentIOCardBaseFsmTaskEntry
    MAX-ACCESS       not-accessible
    STATUS           current
    DESCRIPTION
        "Entry for the cfprEquipmentIOCardBaseFsmTaskTable table."
    INDEX { cfprEquipmentIOCardBaseFsmTaskInstanceId }
    ::= { cfprEquipmentIOCardBaseFsmTaskTable 1 }

CfprEquipmentIOCardBaseFsmTaskEntry ::= SEQUENCE {
    cfprEquipmentIOCardBaseFsmTaskInstanceId                         CfprManagedObjectId,
    cfprEquipmentIOCardBaseFsmTaskDn                                 CfprManagedObjectDn,
    cfprEquipmentIOCardBaseFsmTaskRn                                 SnmpAdminString,
    cfprEquipmentIOCardBaseFsmTaskCompletion                         CfprFsmCompletion,
    cfprEquipmentIOCardBaseFsmTaskFlags                              CfprEquipmentIOCardBaseFsmTaskFlags,
    cfprEquipmentIOCardBaseFsmTaskItem                               CfprEquipmentIOCardBaseFsmTaskItem,
    cfprEquipmentIOCardBaseFsmTaskSeqId                              Gauge32
}

cfprEquipmentIOCardBaseFsmTaskInstanceId OBJECT-TYPE
    SYNTAX       CfprManagedObjectId
    MAX-ACCESS   not-accessible
    STATUS       current
    DESCRIPTION
        "Instance identifier of the managed object."
    ::= { cfprEquipmentIOCardBaseFsmTaskEntry 1 }

cfprEquipmentIOCardBaseFsmTaskDn OBJECT-TYPE
    SYNTAX       CfprManagedObjectDn
    MAX-ACCESS   read-only
    STATUS       current
    DESCRIPTION
        "Cisco Firepower equipment:IOCardBaseFsmTask:dn
        managed object property"
    ::= { cfprEquipmentIOCardBaseFsmTaskEntry 2 }

cfprEquipmentIOCardBaseFsmTaskRn OBJECT-TYPE
    SYNTAX       SnmpAdminString
    MAX-ACCESS   read-only
    STATUS       current
    DESCRIPTION
        "Cisco Firepower equipment:IOCardBaseFsmTask:rn
        managed object property"
    ::= { cfprEquipmentIOCardBaseFsmTaskEntry 3 }

cfprEquipmentIOCardBaseFsmTaskCompletion OBJECT-TYPE
    SYNTAX       CfprFsmCompletion
    MAX-ACCESS   read-only
    STATUS       current
    DESCRIPTION
        "Cisco Firepower equipment:IOCardBaseFsmTask:completion
        managed object property"
    ::= { cfprEquipmentIOCardBaseFsmTaskEntry 4 }

cfprEquipmentIOCardBaseFsmTaskFlags OBJECT-TYPE
    SYNTAX       CfprEquipmentIOCardBaseFsmTaskFlags
    MAX-ACCESS   read-only
    STATUS       current
    DESCRIPTION
        "Cisco Firepower equipment:IOCardBaseFsmTask:flags
        managed object property"
    ::= { cfprEquipmentIOCardBaseFsmTaskEntry 5 }

cfprEquipmentIOCardBaseFsmTaskItem OBJECT-TYPE
    SYNTAX       CfprEquipmentIOCardBaseFsmTaskItem
    MAX-ACCESS   read-only
    STATUS       current
    DESCRIPTION
        "Cisco Firepower equipment:IOCardBaseFsmTask:item
        managed object property"
    ::= { cfprEquipmentIOCardBaseFsmTaskEntry 6 }

cfprEquipmentIOCardBaseFsmTaskSeqId OBJECT-TYPE
    SYNTAX       Gauge32
    MAX-ACCESS   read-only
    STATUS       current
    DESCRIPTION
        "Cisco Firepower equipment:IOCardBaseFsmTask:seqId
        managed object property"
    ::= { cfprEquipmentIOCardBaseFsmTaskEntry 7 }

cfprEquipmentIOCardCapProviderTable OBJECT-TYPE
    SYNTAX           SEQUENCE OF CfprEquipmentIOCardCapProviderEntry
    MAX-ACCESS       not-accessible
    STATUS           current
    DESCRIPTION
        "Cisco Firepower equipment:IOCardCapProvider managed object table"
    ::= { cfprEquipmentObjects 66 }

cfprEquipmentIOCardCapProviderEntry OBJECT-TYPE
    SYNTAX           CfprEquipmentIOCardCapProviderEntry
    MAX-ACCESS       not-accessible
    STATUS           current
    DESCRIPTION
        "Entry for the cfprEquipmentIOCardCapProviderTable table."
    INDEX { cfprEquipmentIOCardCapProviderInstanceId }
    ::= { cfprEquipmentIOCardCapProviderTable 1 }

CfprEquipmentIOCardCapProviderEntry ::= SEQUENCE {
    cfprEquipmentIOCardCapProviderInstanceId                         CfprManagedObjectId,
    cfprEquipmentIOCardCapProviderDn                                 CfprManagedObjectDn,
    cfprEquipmentIOCardCapProviderRn                                 SnmpAdminString,
    cfprEquipmentIOCardCapProviderDeleted                            TruthValue,
    cfprEquipmentIOCardCapProviderDeprecated                         TruthValue,
    cfprEquipmentIOCardCapProviderElementLoadFailures                Gauge32,
    cfprEquipmentIOCardCapProviderElementsLoaded                     Gauge32,
    cfprEquipmentIOCardCapProviderGencount                           Gauge32,
    cfprEquipmentIOCardCapProviderLoadErrors                         Gauge32,
    cfprEquipmentIOCardCapProviderLoadWarnings                       Gauge32,
    cfprEquipmentIOCardCapProviderMgmtPlaneVer                       SnmpAdminString,
    cfprEquipmentIOCardCapProviderModel                              SnmpAdminString,
    cfprEquipmentIOCardCapProviderPromCardType                       Gauge32,
    cfprEquipmentIOCardCapProviderRevision                           SnmpAdminString,
    cfprEquipmentIOCardCapProviderVendor                             SnmpAdminString
}

cfprEquipmentIOCardCapProviderInstanceId OBJECT-TYPE
    SYNTAX       CfprManagedObjectId
    MAX-ACCESS   not-accessible
    STATUS       current
    DESCRIPTION
        "Instance identifier of the managed object."
    ::= { cfprEquipmentIOCardCapProviderEntry 1 }

cfprEquipmentIOCardCapProviderDn OBJECT-TYPE
    SYNTAX       CfprManagedObjectDn
    MAX-ACCESS   read-only
    STATUS       current
    DESCRIPTION
        "Cisco Firepower equipment:IOCardCapProvider:dn
        managed object property"
    ::= { cfprEquipmentIOCardCapProviderEntry 2 }

cfprEquipmentIOCardCapProviderRn OBJECT-TYPE
    SYNTAX       SnmpAdminString
    MAX-ACCESS   read-only
    STATUS       current
    DESCRIPTION
        "Cisco Firepower equipment:IOCardCapProvider:rn
        managed object property"
    ::= { cfprEquipmentIOCardCapProviderEntry 3 }

cfprEquipmentIOCardCapProviderDeleted OBJECT-TYPE
    SYNTAX       TruthValue
    MAX-ACCESS   read-only
    STATUS       current
    DESCRIPTION
        "Cisco Firepower equipment:IOCardCapProvider:deleted
        managed object property"
    ::= { cfprEquipmentIOCardCapProviderEntry 4 }

cfprEquipmentIOCardCapProviderDeprecated OBJECT-TYPE
    SYNTAX       TruthValue
    MAX-ACCESS   read-only
    STATUS       current
    DESCRIPTION
        "Cisco Firepower equipment:IOCardCapProvider:deprecated
        managed object property"
    ::= { cfprEquipmentIOCardCapProviderEntry 5 }

cfprEquipmentIOCardCapProviderElementLoadFailures OBJECT-TYPE
    SYNTAX       Gauge32
    MAX-ACCESS   read-only
    STATUS       current
    DESCRIPTION
        "Cisco Firepower equipment:IOCardCapProvider:elementLoadFailures
        managed object property"
    ::= { cfprEquipmentIOCardCapProviderEntry 6 }

cfprEquipmentIOCardCapProviderElementsLoaded OBJECT-TYPE
    SYNTAX       Gauge32
    MAX-ACCESS   read-only
    STATUS       current
    DESCRIPTION
        "Cisco Firepower equipment:IOCardCapProvider:elementsLoaded
        managed object property"
    ::= { cfprEquipmentIOCardCapProviderEntry 7 }

cfprEquipmentIOCardCapProviderGencount OBJECT-TYPE
    SYNTAX       Gauge32
    MAX-ACCESS   read-only
    STATUS       current
    DESCRIPTION
        "Cisco Firepower equipment:IOCardCapProvider:gencount
        managed object property"
    ::= { cfprEquipmentIOCardCapProviderEntry 8 }

cfprEquipmentIOCardCapProviderLoadErrors OBJECT-TYPE
    SYNTAX       Gauge32
    MAX-ACCESS   read-only
    STATUS       current
    DESCRIPTION
        "Cisco Firepower equipment:IOCardCapProvider:loadErrors
        managed object property"
    ::= { cfprEquipmentIOCardCapProviderEntry 9 }

cfprEquipmentIOCardCapProviderLoadWarnings OBJECT-TYPE
    SYNTAX       Gauge32
    MAX-ACCESS   read-only
    STATUS       current
    DESCRIPTION
        "Cisco Firepower equipment:IOCardCapProvider:loadWarnings
        managed object property"
    ::= { cfprEquipmentIOCardCapProviderEntry 10 }

cfprEquipmentIOCardCapProviderMgmtPlaneVer OBJECT-TYPE
    SYNTAX       SnmpAdminString
    MAX-ACCESS   read-only
    STATUS       current
    DESCRIPTION
        "Cisco Firepower equipment:IOCardCapProvider:mgmtPlaneVer
        managed object property"
    ::= { cfprEquipmentIOCardCapProviderEntry 11 }

cfprEquipmentIOCardCapProviderModel OBJECT-TYPE
    SYNTAX       SnmpAdminString
    MAX-ACCESS   read-only
    STATUS       current
    DESCRIPTION
        "Cisco Firepower equipment:IOCardCapProvider:model
        managed object property"
    ::= { cfprEquipmentIOCardCapProviderEntry 12 }

cfprEquipmentIOCardCapProviderPromCardType OBJECT-TYPE
    SYNTAX       Gauge32
    MAX-ACCESS   read-only
    STATUS       current
    DESCRIPTION
        "Cisco Firepower equipment:IOCardCapProvider:promCardType
        managed object property"
    ::= { cfprEquipmentIOCardCapProviderEntry 13 }

cfprEquipmentIOCardCapProviderRevision OBJECT-TYPE
    SYNTAX       SnmpAdminString
    MAX-ACCESS   read-only
    STATUS       current
    DESCRIPTION
        "Cisco Firepower equipment:IOCardCapProvider:revision
        managed object property"
    ::= { cfprEquipmentIOCardCapProviderEntry 14 }

cfprEquipmentIOCardCapProviderVendor OBJECT-TYPE
    SYNTAX       SnmpAdminString
    MAX-ACCESS   read-only
    STATUS       current
    DESCRIPTION
        "Cisco Firepower equipment:IOCardCapProvider:vendor
        managed object property"
    ::= { cfprEquipmentIOCardCapProviderEntry 15 }

cfprEquipmentIOCardFsmTable OBJECT-TYPE
    SYNTAX           SEQUENCE OF CfprEquipmentIOCardFsmEntry
    MAX-ACCESS       not-accessible
    STATUS           current
    DESCRIPTION
        "Cisco Firepower equipment:IOCardFsm managed object table"
    ::= { cfprEquipmentObjects 67 }

cfprEquipmentIOCardFsmEntry OBJECT-TYPE
    SYNTAX           CfprEquipmentIOCardFsmEntry
    MAX-ACCESS       not-accessible
    STATUS           current
    DESCRIPTION
        "Entry for the cfprEquipmentIOCardFsmTable table."
    INDEX { cfprEquipmentIOCardFsmInstanceId }
    ::= { cfprEquipmentIOCardFsmTable 1 }

CfprEquipmentIOCardFsmEntry ::= SEQUENCE {
    cfprEquipmentIOCardFsmInstanceId                                 CfprManagedObjectId,
    cfprEquipmentIOCardFsmDn                                         CfprManagedObjectDn,
    cfprEquipmentIOCardFsmRn                                         SnmpAdminString,
    cfprEquipmentIOCardFsmCompletionTime                             DateAndTime,
    cfprEquipmentIOCardFsmCurrentFsm                                 CfprEquipmentIOCardFsmCurrentFsm,
    cfprEquipmentIOCardFsmDescrData                                  SnmpAdminString,
    cfprEquipmentIOCardFsmFsmStatus                                  CfprFsmFsmStageStatus,
    cfprEquipmentIOCardFsmProgress                                   Gauge32,
    cfprEquipmentIOCardFsmRmtErrCode                                 Gauge32,
    cfprEquipmentIOCardFsmRmtErrDescr                                SnmpAdminString,
    cfprEquipmentIOCardFsmRmtRslt                                    CfprConditionRemoteInvRslt
}

cfprEquipmentIOCardFsmInstanceId OBJECT-TYPE
    SYNTAX       CfprManagedObjectId
    MAX-ACCESS   not-accessible
    STATUS       current
    DESCRIPTION
        "Instance identifier of the managed object."
    ::= { cfprEquipmentIOCardFsmEntry 1 }

cfprEquipmentIOCardFsmDn OBJECT-TYPE
    SYNTAX       CfprManagedObjectDn
    MAX-ACCESS   read-only
    STATUS       current
    DESCRIPTION
        "Cisco Firepower equipment:IOCardFsm:dn managed object property"
    ::= { cfprEquipmentIOCardFsmEntry 2 }

cfprEquipmentIOCardFsmRn OBJECT-TYPE
    SYNTAX       SnmpAdminString
    MAX-ACCESS   read-only
    STATUS       current
    DESCRIPTION
        "Cisco Firepower equipment:IOCardFsm:rn managed object property"
    ::= { cfprEquipmentIOCardFsmEntry 3 }

cfprEquipmentIOCardFsmCompletionTime OBJECT-TYPE
    SYNTAX       DateAndTime
    MAX-ACCESS   read-only
    STATUS       current
    DESCRIPTION
        "Cisco Firepower equipment:IOCardFsm:completionTime
        managed object property"
    ::= { cfprEquipmentIOCardFsmEntry 4 }

cfprEquipmentIOCardFsmCurrentFsm OBJECT-TYPE
    SYNTAX       CfprEquipmentIOCardFsmCurrentFsm
    MAX-ACCESS   read-only
    STATUS       current
    DESCRIPTION
        "Cisco Firepower equipment:IOCardFsm:currentFsm
        managed object property"
    ::= { cfprEquipmentIOCardFsmEntry 5 }

cfprEquipmentIOCardFsmDescrData OBJECT-TYPE
    SYNTAX       SnmpAdminString
    MAX-ACCESS   read-only
    STATUS       current
    DESCRIPTION
        "Cisco Firepower equipment:IOCardFsm:descr managed
        object property"
    ::= { cfprEquipmentIOCardFsmEntry 6 }

cfprEquipmentIOCardFsmFsmStatus OBJECT-TYPE
    SYNTAX       CfprFsmFsmStageStatus
    MAX-ACCESS   read-only
    STATUS       current
    DESCRIPTION
        "Cisco Firepower equipment:IOCardFsm:fsmStatus
        managed object property"
    ::= { cfprEquipmentIOCardFsmEntry 7 }

cfprEquipmentIOCardFsmProgress OBJECT-TYPE
    SYNTAX       Gauge32
    MAX-ACCESS   read-only
    STATUS       current
    DESCRIPTION
        "Cisco Firepower equipment:IOCardFsm:progress managed
        object property"
    ::= { cfprEquipmentIOCardFsmEntry 8 }

cfprEquipmentIOCardFsmRmtErrCode OBJECT-TYPE
    SYNTAX       Gauge32
    MAX-ACCESS   read-only
    STATUS       current
    DESCRIPTION
        "Cisco Firepower equipment:IOCardFsm:rmtErrCode
        managed object property"
    ::= { cfprEquipmentIOCardFsmEntry 9 }

cfprEquipmentIOCardFsmRmtErrDescr OBJECT-TYPE
    SYNTAX       SnmpAdminString
    MAX-ACCESS   read-only
    STATUS       current
    DESCRIPTION
        "Cisco Firepower equipment:IOCardFsm:rmtErrDescr
        managed object property"
    ::= { cfprEquipmentIOCardFsmEntry 10 }

cfprEquipmentIOCardFsmRmtRslt OBJECT-TYPE
    SYNTAX       CfprConditionRemoteInvRslt
    MAX-ACCESS   read-only
    STATUS       current
    DESCRIPTION
        "Cisco Firepower equipment:IOCardFsm:rmtRslt managed
        object property"
    ::= { cfprEquipmentIOCardFsmEntry 11 }

cfprEquipmentIOCardFsmStageTable OBJECT-TYPE
    SYNTAX           SEQUENCE OF CfprEquipmentIOCardFsmStageEntry
    MAX-ACCESS       not-accessible
    STATUS           current
    DESCRIPTION
        "Cisco Firepower equipment:IOCardFsmStage managed object table"
    ::= { cfprEquipmentObjects 68 }

cfprEquipmentIOCardFsmStageEntry OBJECT-TYPE
    SYNTAX           CfprEquipmentIOCardFsmStageEntry
    MAX-ACCESS       not-accessible
    STATUS           current
    DESCRIPTION
        "Entry for the cfprEquipmentIOCardFsmStageTable table."
    INDEX { cfprEquipmentIOCardFsmStageInstanceId }
    ::= { cfprEquipmentIOCardFsmStageTable 1 }

CfprEquipmentIOCardFsmStageEntry ::= SEQUENCE {
    cfprEquipmentIOCardFsmStageInstanceId                            CfprManagedObjectId,
    cfprEquipmentIOCardFsmStageDn                                    CfprManagedObjectDn,
    cfprEquipmentIOCardFsmStageRn                                    SnmpAdminString,
    cfprEquipmentIOCardFsmStageDescrData                             SnmpAdminString,
    cfprEquipmentIOCardFsmStageLastUpdateTime                        DateAndTime,
    cfprEquipmentIOCardFsmStageName                                  CfprEquipmentIOCardFsmStageName,
    cfprEquipmentIOCardFsmStageOrder                                 Gauge32,
    cfprEquipmentIOCardFsmStageRetry                                 Gauge32,
    cfprEquipmentIOCardFsmStageStageStatus                           CfprFsmFsmStageStatus
}

cfprEquipmentIOCardFsmStageInstanceId OBJECT-TYPE
    SYNTAX       CfprManagedObjectId
    MAX-ACCESS   not-accessible
    STATUS       current
    DESCRIPTION
        "Instance identifier of the managed object."
    ::= { cfprEquipmentIOCardFsmStageEntry 1 }

cfprEquipmentIOCardFsmStageDn OBJECT-TYPE
    SYNTAX       CfprManagedObjectDn
    MAX-ACCESS   read-only
    STATUS       current
    DESCRIPTION
        "Cisco Firepower equipment:IOCardFsmStage:dn managed
        object property"
    ::= { cfprEquipmentIOCardFsmStageEntry 2 }

cfprEquipmentIOCardFsmStageRn OBJECT-TYPE
    SYNTAX       SnmpAdminString
    MAX-ACCESS   read-only
    STATUS       current
    DESCRIPTION
        "Cisco Firepower equipment:IOCardFsmStage:rn managed
        object property"
    ::= { cfprEquipmentIOCardFsmStageEntry 3 }

cfprEquipmentIOCardFsmStageDescrData OBJECT-TYPE
    SYNTAX       SnmpAdminString
    MAX-ACCESS   read-only
    STATUS       current
    DESCRIPTION
        "Cisco Firepower equipment:IOCardFsmStage:descr
        managed object property"
    ::= { cfprEquipmentIOCardFsmStageEntry 4 }

cfprEquipmentIOCardFsmStageLastUpdateTime OBJECT-TYPE
    SYNTAX       DateAndTime
    MAX-ACCESS   read-only
    STATUS       current
    DESCRIPTION
        "Cisco Firepower equipment:IOCardFsmStage:lastUpdateTime
        managed object property"
    ::= { cfprEquipmentIOCardFsmStageEntry 5 }

cfprEquipmentIOCardFsmStageName OBJECT-TYPE
    SYNTAX       CfprEquipmentIOCardFsmStageName
    MAX-ACCESS   read-only
    STATUS       current
    DESCRIPTION
        "Cisco Firepower equipment:IOCardFsmStage:name
        managed object property"
    ::= { cfprEquipmentIOCardFsmStageEntry 6 }

cfprEquipmentIOCardFsmStageOrder OBJECT-TYPE
    SYNTAX       Gauge32
    MAX-ACCESS   read-only
    STATUS       current
    DESCRIPTION
        "Cisco Firepower equipment:IOCardFsmStage:order
        managed object property"
    ::= { cfprEquipmentIOCardFsmStageEntry 7 }

cfprEquipmentIOCardFsmStageRetry OBJECT-TYPE
    SYNTAX       Gauge32
    MAX-ACCESS   read-only
    STATUS       current
    DESCRIPTION
        "Cisco Firepower equipment:IOCardFsmStage:retry
        managed object property"
    ::= { cfprEquipmentIOCardFsmStageEntry 8 }

cfprEquipmentIOCardFsmStageStageStatus OBJECT-TYPE
    SYNTAX       CfprFsmFsmStageStatus
    MAX-ACCESS   read-only
    STATUS       current
    DESCRIPTION
        "Cisco Firepower equipment:IOCardFsmStage:stageStatus
        managed object property"
    ::= { cfprEquipmentIOCardFsmStageEntry 9 }

cfprEquipmentIOCardFsmTaskTable OBJECT-TYPE
    SYNTAX           SEQUENCE OF CfprEquipmentIOCardFsmTaskEntry
    MAX-ACCESS       not-accessible
    STATUS           current
    DESCRIPTION
        "Cisco Firepower equipment:IOCardFsmTask managed object table"
    ::= { cfprEquipmentObjects 69 }

cfprEquipmentIOCardFsmTaskEntry OBJECT-TYPE
    SYNTAX           CfprEquipmentIOCardFsmTaskEntry
    MAX-ACCESS       not-accessible
    STATUS           current
    DESCRIPTION
        "Entry for the cfprEquipmentIOCardFsmTaskTable table."
    INDEX { cfprEquipmentIOCardFsmTaskInstanceId }
    ::= { cfprEquipmentIOCardFsmTaskTable 1 }

CfprEquipmentIOCardFsmTaskEntry ::= SEQUENCE {
    cfprEquipmentIOCardFsmTaskInstanceId                             CfprManagedObjectId,
    cfprEquipmentIOCardFsmTaskDn                                     CfprManagedObjectDn,
    cfprEquipmentIOCardFsmTaskRn                                     SnmpAdminString,
    cfprEquipmentIOCardFsmTaskCompletion                             CfprFsmCompletion,
    cfprEquipmentIOCardFsmTaskFlags                                  CfprFsmFlags,
    cfprEquipmentIOCardFsmTaskItem                                   CfprEquipmentIOCardFsmTaskItem,
    cfprEquipmentIOCardFsmTaskSeqId                                  Gauge32
}

cfprEquipmentIOCardFsmTaskInstanceId OBJECT-TYPE
    SYNTAX       CfprManagedObjectId
    MAX-ACCESS   not-accessible
    STATUS       current
    DESCRIPTION
        "Instance identifier of the managed object."
    ::= { cfprEquipmentIOCardFsmTaskEntry 1 }

cfprEquipmentIOCardFsmTaskDn OBJECT-TYPE
    SYNTAX       CfprManagedObjectDn
    MAX-ACCESS   read-only
    STATUS       current
    DESCRIPTION
        "Cisco Firepower equipment:IOCardFsmTask:dn managed
        object property"
    ::= { cfprEquipmentIOCardFsmTaskEntry 2 }

cfprEquipmentIOCardFsmTaskRn OBJECT-TYPE
    SYNTAX       SnmpAdminString
    MAX-ACCESS   read-only
    STATUS       current
    DESCRIPTION
        "Cisco Firepower equipment:IOCardFsmTask:rn managed
        object property"
    ::= { cfprEquipmentIOCardFsmTaskEntry 3 }

cfprEquipmentIOCardFsmTaskCompletion OBJECT-TYPE
    SYNTAX       CfprFsmCompletion
    MAX-ACCESS   read-only
    STATUS       current
    DESCRIPTION
        "Cisco Firepower equipment:IOCardFsmTask:completion
        managed object property"
    ::= { cfprEquipmentIOCardFsmTaskEntry 4 }

cfprEquipmentIOCardFsmTaskFlags OBJECT-TYPE
    SYNTAX       CfprFsmFlags
    MAX-ACCESS   read-only
    STATUS       current
    DESCRIPTION
        "Cisco Firepower equipment:IOCardFsmTask:flags
        managed object property"
    ::= { cfprEquipmentIOCardFsmTaskEntry 5 }

cfprEquipmentIOCardFsmTaskItem OBJECT-TYPE
    SYNTAX       CfprEquipmentIOCardFsmTaskItem
    MAX-ACCESS   read-only
    STATUS       current
    DESCRIPTION
        "Cisco Firepower equipment:IOCardFsmTask:item managed
        object property"
    ::= { cfprEquipmentIOCardFsmTaskEntry 6 }

cfprEquipmentIOCardFsmTaskSeqId OBJECT-TYPE
    SYNTAX       Gauge32
    MAX-ACCESS   read-only
    STATUS       current
    DESCRIPTION
        "Cisco Firepower equipment:IOCardFsmTask:seqId
        managed object property"
    ::= { cfprEquipmentIOCardFsmTaskEntry 7 }

cfprEquipmentIOCardStatsTable OBJECT-TYPE
    SYNTAX           SEQUENCE OF CfprEquipmentIOCardStatsEntry
    MAX-ACCESS       not-accessible
    STATUS           current
    DESCRIPTION
        "Cisco Firepower equipment:IOCardStats managed object table"
    ::= { cfprEquipmentObjects 70 }

cfprEquipmentIOCardStatsEntry OBJECT-TYPE
    SYNTAX           CfprEquipmentIOCardStatsEntry
    MAX-ACCESS       not-accessible
    STATUS           current
    DESCRIPTION
        "Entry for the cfprEquipmentIOCardStatsTable table."
    INDEX { cfprEquipmentIOCardStatsInstanceId }
    ::= { cfprEquipmentIOCardStatsTable 1 }

CfprEquipmentIOCardStatsEntry ::= SEQUENCE {
    cfprEquipmentIOCardStatsInstanceId                               CfprManagedObjectId,
    cfprEquipmentIOCardStatsDn                                       CfprManagedObjectDn,
    cfprEquipmentIOCardStatsRn                                       SnmpAdminString,
    cfprEquipmentIOCardStatsAmbientTemp                              INTEGER,
    cfprEquipmentIOCardStatsAmbientTempAvg                           INTEGER,
    cfprEquipmentIOCardStatsAmbientTempMax                           INTEGER,
    cfprEquipmentIOCardStatsAmbientTempMin                           INTEGER,
    cfprEquipmentIOCardStatsDimmTemp                                 INTEGER,
    cfprEquipmentIOCardStatsDimmTempAvg                              INTEGER,
    cfprEquipmentIOCardStatsDimmTempMax                              INTEGER,
    cfprEquipmentIOCardStatsDimmTempMin                              INTEGER,
    cfprEquipmentIOCardStatsIntervals                                Gauge32,
    cfprEquipmentIOCardStatsProcTemp                                 INTEGER,
    cfprEquipmentIOCardStatsProcTempAvg                              INTEGER,
    cfprEquipmentIOCardStatsProcTempMax                              INTEGER,
    cfprEquipmentIOCardStatsProcTempMin                              INTEGER,
    cfprEquipmentIOCardStatsSuspect                                  TruthValue,
    cfprEquipmentIOCardStatsTemp                                     INTEGER,
    cfprEquipmentIOCardStatsTempAvg                                  INTEGER,
    cfprEquipmentIOCardStatsTempMax                                  INTEGER,
    cfprEquipmentIOCardStatsTempMin                                  INTEGER,
    cfprEquipmentIOCardStatsThresholded                              CfprEquipmentIOCardStatsThresholded,
    cfprEquipmentIOCardStatsTimeCollected                            DateAndTime,
    cfprEquipmentIOCardStatsUpdate                                   Gauge32
}

cfprEquipmentIOCardStatsInstanceId OBJECT-TYPE
    SYNTAX       CfprManagedObjectId
    MAX-ACCESS   not-accessible
    STATUS       current
    DESCRIPTION
        "Instance identifier of the managed object."
    ::= { cfprEquipmentIOCardStatsEntry 1 }

cfprEquipmentIOCardStatsDn OBJECT-TYPE
    SYNTAX       CfprManagedObjectDn
    MAX-ACCESS   read-only
    STATUS       current
    DESCRIPTION
        "Cisco Firepower equipment:IOCardStats:dn managed object property"
    ::= { cfprEquipmentIOCardStatsEntry 2 }

cfprEquipmentIOCardStatsRn OBJECT-TYPE
    SYNTAX       SnmpAdminString
    MAX-ACCESS   read-only
    STATUS       current
    DESCRIPTION
        "Cisco Firepower equipment:IOCardStats:rn managed object property"
    ::= { cfprEquipmentIOCardStatsEntry 3 }

cfprEquipmentIOCardStatsAmbientTemp OBJECT-TYPE
    SYNTAX       INTEGER
    MAX-ACCESS   read-only
    STATUS       current
    DESCRIPTION
        "Cisco Firepower equipment:IOCardStats:ambientTemp
        managed object property"
    ::= { cfprEquipmentIOCardStatsEntry 4 }

cfprEquipmentIOCardStatsAmbientTempAvg OBJECT-TYPE
    SYNTAX       INTEGER
    MAX-ACCESS   read-only
    STATUS       current
    DESCRIPTION
        "Cisco Firepower equipment:IOCardStats:ambientTempAvg
        managed object property"
    ::= { cfprEquipmentIOCardStatsEntry 5 }

cfprEquipmentIOCardStatsAmbientTempMax OBJECT-TYPE
    SYNTAX       INTEGER
    MAX-ACCESS   read-only
    STATUS       current
    DESCRIPTION
        "Cisco Firepower equipment:IOCardStats:ambientTempMax
        managed object property"
    ::= { cfprEquipmentIOCardStatsEntry 6 }

cfprEquipmentIOCardStatsAmbientTempMin OBJECT-TYPE
    SYNTAX       INTEGER
    MAX-ACCESS   read-only
    STATUS       current
    DESCRIPTION
        "Cisco Firepower equipment:IOCardStats:ambientTempMin
        managed object property"
    ::= { cfprEquipmentIOCardStatsEntry 7 }

cfprEquipmentIOCardStatsDimmTemp OBJECT-TYPE
    SYNTAX       INTEGER
    MAX-ACCESS   read-only
    STATUS       current
    DESCRIPTION
        "Cisco Firepower equipment:IOCardStats:dimmTemp
        managed object property"
    ::= { cfprEquipmentIOCardStatsEntry 8 }

cfprEquipmentIOCardStatsDimmTempAvg OBJECT-TYPE
    SYNTAX       INTEGER
    MAX-ACCESS   read-only
    STATUS       current
    DESCRIPTION
        "Cisco Firepower equipment:IOCardStats:dimmTempAvg
        managed object property"
    ::= { cfprEquipmentIOCardStatsEntry 9 }

cfprEquipmentIOCardStatsDimmTempMax OBJECT-TYPE
    SYNTAX       INTEGER
    MAX-ACCESS   read-only
    STATUS       current
    DESCRIPTION
        "Cisco Firepower equipment:IOCardStats:dimmTempMax
        managed object property"
    ::= { cfprEquipmentIOCardStatsEntry 10 }

cfprEquipmentIOCardStatsDimmTempMin OBJECT-TYPE
    SYNTAX       INTEGER
    MAX-ACCESS   read-only
    STATUS       current
    DESCRIPTION
        "Cisco Firepower equipment:IOCardStats:dimmTempMin
        managed object property"
    ::= { cfprEquipmentIOCardStatsEntry 11 }

cfprEquipmentIOCardStatsIntervals OBJECT-TYPE
    SYNTAX       Gauge32
    MAX-ACCESS   read-only
    STATUS       current
    DESCRIPTION
        "Cisco Firepower equipment:IOCardStats:intervals
        managed object property"
    ::= { cfprEquipmentIOCardStatsEntry 12 }

cfprEquipmentIOCardStatsProcTemp OBJECT-TYPE
    SYNTAX       INTEGER
    MAX-ACCESS   read-only
    STATUS       current
    DESCRIPTION
        "Cisco Firepower equipment:IOCardStats:procTemp
        managed object property"
    ::= { cfprEquipmentIOCardStatsEntry 13 }

cfprEquipmentIOCardStatsProcTempAvg OBJECT-TYPE
    SYNTAX       INTEGER
    MAX-ACCESS   read-only
    STATUS       current
    DESCRIPTION
        "Cisco Firepower equipment:IOCardStats:procTempAvg
        managed object property"
    ::= { cfprEquipmentIOCardStatsEntry 14 }

cfprEquipmentIOCardStatsProcTempMax OBJECT-TYPE
    SYNTAX       INTEGER
    MAX-ACCESS   read-only
    STATUS       current
    DESCRIPTION
        "Cisco Firepower equipment:IOCardStats:procTempMax
        managed object property"
    ::= { cfprEquipmentIOCardStatsEntry 15 }

cfprEquipmentIOCardStatsProcTempMin OBJECT-TYPE
    SYNTAX       INTEGER
    MAX-ACCESS   read-only
    STATUS       current
    DESCRIPTION
        "Cisco Firepower equipment:IOCardStats:procTempMin
        managed object property"
    ::= { cfprEquipmentIOCardStatsEntry 16 }

cfprEquipmentIOCardStatsSuspect OBJECT-TYPE
    SYNTAX       TruthValue
    MAX-ACCESS   read-only
    STATUS       current
    DESCRIPTION
        "Cisco Firepower equipment:IOCardStats:suspect
        managed object property"
    ::= { cfprEquipmentIOCardStatsEntry 17 }

cfprEquipmentIOCardStatsTemp OBJECT-TYPE
    SYNTAX       INTEGER
    MAX-ACCESS   read-only
    STATUS       current
    DESCRIPTION
        "Cisco Firepower equipment:IOCardStats:temp managed
        object property"
    ::= { cfprEquipmentIOCardStatsEntry 18 }

cfprEquipmentIOCardStatsTempAvg OBJECT-TYPE
    SYNTAX       INTEGER
    MAX-ACCESS   read-only
    STATUS       current
    DESCRIPTION
        "Cisco Firepower equipment:IOCardStats:tempAvg
        managed object property"
    ::= { cfprEquipmentIOCardStatsEntry 19 }

cfprEquipmentIOCardStatsTempMax OBJECT-TYPE
    SYNTAX       INTEGER
    MAX-ACCESS   read-only
    STATUS       current
    DESCRIPTION
        "Cisco Firepower equipment:IOCardStats:tempMax
        managed object property"
    ::= { cfprEquipmentIOCardStatsEntry 20 }

cfprEquipmentIOCardStatsTempMin OBJECT-TYPE
    SYNTAX       INTEGER
    MAX-ACCESS   read-only
    STATUS       current
    DESCRIPTION
        "Cisco Firepower equipment:IOCardStats:tempMin
        managed object property"
    ::= { cfprEquipmentIOCardStatsEntry 21 }

cfprEquipmentIOCardStatsThresholded OBJECT-TYPE
    SYNTAX       CfprEquipmentIOCardStatsThresholded
    MAX-ACCESS   read-only
    STATUS       current
    DESCRIPTION
        "Cisco Firepower equipment:IOCardStats:thresholded
        managed object property"
    ::= { cfprEquipmentIOCardStatsEntry 22 }

cfprEquipmentIOCardStatsTimeCollected OBJECT-TYPE
    SYNTAX       DateAndTime
    MAX-ACCESS   read-only
    STATUS       current
    DESCRIPTION
        "Cisco Firepower equipment:IOCardStats:timeCollected
        managed object property"
    ::= { cfprEquipmentIOCardStatsEntry 23 }

cfprEquipmentIOCardStatsUpdate OBJECT-TYPE
    SYNTAX       Gauge32
    MAX-ACCESS   read-only
    STATUS       current
    DESCRIPTION
        "Cisco Firepower equipment:IOCardStats:update managed
        object property"
    ::= { cfprEquipmentIOCardStatsEntry 24 }

cfprEquipmentIOCardStatsHistTable OBJECT-TYPE
    SYNTAX           SEQUENCE OF CfprEquipmentIOCardStatsHistEntry
    MAX-ACCESS       not-accessible
    STATUS           current
    DESCRIPTION
        "Cisco Firepower equipment:IOCardStatsHist managed object table"
    ::= { cfprEquipmentObjects 71 }

cfprEquipmentIOCardStatsHistEntry OBJECT-TYPE
    SYNTAX           CfprEquipmentIOCardStatsHistEntry
    MAX-ACCESS       not-accessible
    STATUS           current
    DESCRIPTION
        "Entry for the cfprEquipmentIOCardStatsHistTable table."
    INDEX { cfprEquipmentIOCardStatsHistInstanceId }
    ::= { cfprEquipmentIOCardStatsHistTable 1 }

CfprEquipmentIOCardStatsHistEntry ::= SEQUENCE {
    cfprEquipmentIOCardStatsHistInstanceId                           CfprManagedObjectId,
    cfprEquipmentIOCardStatsHistDn                                   CfprManagedObjectDn,
    cfprEquipmentIOCardStatsHistRn                                   SnmpAdminString,
    cfprEquipmentIOCardStatsHistAmbientTemp                          INTEGER,
    cfprEquipmentIOCardStatsHistAmbientTempAvg                       INTEGER,
    cfprEquipmentIOCardStatsHistAmbientTempMax                       INTEGER,
    cfprEquipmentIOCardStatsHistAmbientTempMin                       INTEGER,
    cfprEquipmentIOCardStatsHistDimmTemp                             INTEGER,
    cfprEquipmentIOCardStatsHistDimmTempAvg                          INTEGER,
    cfprEquipmentIOCardStatsHistDimmTempMax                          INTEGER,
    cfprEquipmentIOCardStatsHistDimmTempMin                          INTEGER,
    cfprEquipmentIOCardStatsHistId                                   Unsigned64,
    cfprEquipmentIOCardStatsHistMostRecent                           TruthValue,
    cfprEquipmentIOCardStatsHistProcTemp                             INTEGER,
    cfprEquipmentIOCardStatsHistProcTempAvg                          INTEGER,
    cfprEquipmentIOCardStatsHistProcTempMax                          INTEGER,
    cfprEquipmentIOCardStatsHistProcTempMin                          INTEGER,
    cfprEquipmentIOCardStatsHistSuspect                              TruthValue,
    cfprEquipmentIOCardStatsHistTemp                                 INTEGER,
    cfprEquipmentIOCardStatsHistTempAvg                              INTEGER,
    cfprEquipmentIOCardStatsHistTempMax                              INTEGER,
    cfprEquipmentIOCardStatsHistTempMin                              INTEGER,
    cfprEquipmentIOCardStatsHistThresholded                          CfprEquipmentIOCardStatsHistThresholded,
    cfprEquipmentIOCardStatsHistTimeCollected                        DateAndTime
}

cfprEquipmentIOCardStatsHistInstanceId OBJECT-TYPE
    SYNTAX       CfprManagedObjectId
    MAX-ACCESS   not-accessible
    STATUS       current
    DESCRIPTION
        "Instance identifier of the managed object."
    ::= { cfprEquipmentIOCardStatsHistEntry 1 }

cfprEquipmentIOCardStatsHistDn OBJECT-TYPE
    SYNTAX       CfprManagedObjectDn
    MAX-ACCESS   read-only
    STATUS       current
    DESCRIPTION
        "Cisco Firepower equipment:IOCardStatsHist:dn managed
        object property"
    ::= { cfprEquipmentIOCardStatsHistEntry 2 }

cfprEquipmentIOCardStatsHistRn OBJECT-TYPE
    SYNTAX       SnmpAdminString
    MAX-ACCESS   read-only
    STATUS       current
    DESCRIPTION
        "Cisco Firepower equipment:IOCardStatsHist:rn managed
        object property"
    ::= { cfprEquipmentIOCardStatsHistEntry 3 }

cfprEquipmentIOCardStatsHistAmbientTemp OBJECT-TYPE
    SYNTAX       INTEGER
    MAX-ACCESS   read-only
    STATUS       current
    DESCRIPTION
        "Cisco Firepower equipment:IOCardStatsHist:ambientTemp
        managed object property"
    ::= { cfprEquipmentIOCardStatsHistEntry 4 }

cfprEquipmentIOCardStatsHistAmbientTempAvg OBJECT-TYPE
    SYNTAX       INTEGER
    MAX-ACCESS   read-only
    STATUS       current
    DESCRIPTION
        "Cisco Firepower equipment:IOCardStatsHist:ambientTempAvg
        managed object property"
    ::= { cfprEquipmentIOCardStatsHistEntry 5 }

cfprEquipmentIOCardStatsHistAmbientTempMax OBJECT-TYPE
    SYNTAX       INTEGER
    MAX-ACCESS   read-only
    STATUS       current
    DESCRIPTION
        "Cisco Firepower equipment:IOCardStatsHist:ambientTempMax
        managed object property"
    ::= { cfprEquipmentIOCardStatsHistEntry 6 }

cfprEquipmentIOCardStatsHistAmbientTempMin OBJECT-TYPE
    SYNTAX       INTEGER
    MAX-ACCESS   read-only
    STATUS       current
    DESCRIPTION
        "Cisco Firepower equipment:IOCardStatsHist:ambientTempMin
        managed object property"
    ::= { cfprEquipmentIOCardStatsHistEntry 7 }

cfprEquipmentIOCardStatsHistDimmTemp OBJECT-TYPE
    SYNTAX       INTEGER
    MAX-ACCESS   read-only
    STATUS       current
    DESCRIPTION
        "Cisco Firepower equipment:IOCardStatsHist:dimmTemp
        managed object property"
    ::= { cfprEquipmentIOCardStatsHistEntry 8 }

cfprEquipmentIOCardStatsHistDimmTempAvg OBJECT-TYPE
    SYNTAX       INTEGER
    MAX-ACCESS   read-only
    STATUS       current
    DESCRIPTION
        "Cisco Firepower equipment:IOCardStatsHist:dimmTempAvg
        managed object property"
    ::= { cfprEquipmentIOCardStatsHistEntry 9 }

cfprEquipmentIOCardStatsHistDimmTempMax OBJECT-TYPE
    SYNTAX       INTEGER
    MAX-ACCESS   read-only
    STATUS       current
    DESCRIPTION
        "Cisco Firepower equipment:IOCardStatsHist:dimmTempMax
        managed object property"
    ::= { cfprEquipmentIOCardStatsHistEntry 10 }

cfprEquipmentIOCardStatsHistDimmTempMin OBJECT-TYPE
    SYNTAX       INTEGER
    MAX-ACCESS   read-only
    STATUS       current
    DESCRIPTION
        "Cisco Firepower equipment:IOCardStatsHist:dimmTempMin
        managed object property"
    ::= { cfprEquipmentIOCardStatsHistEntry 11 }

cfprEquipmentIOCardStatsHistId OBJECT-TYPE
    SYNTAX       Unsigned64
    MAX-ACCESS   read-only
    STATUS       current
    DESCRIPTION
        "Cisco Firepower equipment:IOCardStatsHist:id managed
        object property"
    ::= { cfprEquipmentIOCardStatsHistEntry 12 }

cfprEquipmentIOCardStatsHistMostRecent OBJECT-TYPE
    SYNTAX       TruthValue
    MAX-ACCESS   read-only
    STATUS       current
    DESCRIPTION
        "Cisco Firepower equipment:IOCardStatsHist:mostRecent
        managed object property"
    ::= { cfprEquipmentIOCardStatsHistEntry 13 }

cfprEquipmentIOCardStatsHistProcTemp OBJECT-TYPE
    SYNTAX       INTEGER
    MAX-ACCESS   read-only
    STATUS       current
    DESCRIPTION
        "Cisco Firepower equipment:IOCardStatsHist:procTemp
        managed object property"
    ::= { cfprEquipmentIOCardStatsHistEntry 14 }

cfprEquipmentIOCardStatsHistProcTempAvg OBJECT-TYPE
    SYNTAX       INTEGER
    MAX-ACCESS   read-only
    STATUS       current
    DESCRIPTION
        "Cisco Firepower equipment:IOCardStatsHist:procTempAvg
        managed object property"
    ::= { cfprEquipmentIOCardStatsHistEntry 15 }

cfprEquipmentIOCardStatsHistProcTempMax OBJECT-TYPE
    SYNTAX       INTEGER
    MAX-ACCESS   read-only
    STATUS       current
    DESCRIPTION
        "Cisco Firepower equipment:IOCardStatsHist:procTempMax
        managed object property"
    ::= { cfprEquipmentIOCardStatsHistEntry 16 }

cfprEquipmentIOCardStatsHistProcTempMin OBJECT-TYPE
    SYNTAX       INTEGER
    MAX-ACCESS   read-only
    STATUS       current
    DESCRIPTION
        "Cisco Firepower equipment:IOCardStatsHist:procTempMin
        managed object property"
    ::= { cfprEquipmentIOCardStatsHistEntry 17 }

cfprEquipmentIOCardStatsHistSuspect OBJECT-TYPE
    SYNTAX       TruthValue
    MAX-ACCESS   read-only
    STATUS       current
    DESCRIPTION
        "Cisco Firepower equipment:IOCardStatsHist:suspect
        managed object property"
    ::= { cfprEquipmentIOCardStatsHistEntry 18 }

cfprEquipmentIOCardStatsHistTemp OBJECT-TYPE
    SYNTAX       INTEGER
    MAX-ACCESS   read-only
    STATUS       current
    DESCRIPTION
        "Cisco Firepower equipment:IOCardStatsHist:temp
        managed object property"
    ::= { cfprEquipmentIOCardStatsHistEntry 19 }

cfprEquipmentIOCardStatsHistTempAvg OBJECT-TYPE
    SYNTAX       INTEGER
    MAX-ACCESS   read-only
    STATUS       current
    DESCRIPTION
        "Cisco Firepower equipment:IOCardStatsHist:tempAvg
        managed object property"
    ::= { cfprEquipmentIOCardStatsHistEntry 20 }

cfprEquipmentIOCardStatsHistTempMax OBJECT-TYPE
    SYNTAX       INTEGER
    MAX-ACCESS   read-only
    STATUS       current
    DESCRIPTION
        "Cisco Firepower equipment:IOCardStatsHist:tempMax
        managed object property"
    ::= { cfprEquipmentIOCardStatsHistEntry 21 }

cfprEquipmentIOCardStatsHistTempMin OBJECT-TYPE
    SYNTAX       INTEGER
    MAX-ACCESS   read-only
    STATUS       current
    DESCRIPTION
        "Cisco Firepower equipment:IOCardStatsHist:tempMin
        managed object property"
    ::= { cfprEquipmentIOCardStatsHistEntry 22 }

cfprEquipmentIOCardStatsHistThresholded OBJECT-TYPE
    SYNTAX       CfprEquipmentIOCardStatsHistThresholded
    MAX-ACCESS   read-only
    STATUS       current
    DESCRIPTION
        "Cisco Firepower equipment:IOCardStatsHist:thresholded
        managed object property"
    ::= { cfprEquipmentIOCardStatsHistEntry 23 }

cfprEquipmentIOCardStatsHistTimeCollected OBJECT-TYPE
    SYNTAX       DateAndTime
    MAX-ACCESS   read-only
    STATUS       current
    DESCRIPTION
        "Cisco Firepower equipment:IOCardStatsHist:timeCollected
        managed object property"
    ::= { cfprEquipmentIOCardStatsHistEntry 24 }

cfprEquipmentIOCardTypeDefTable OBJECT-TYPE
    SYNTAX           SEQUENCE OF CfprEquipmentIOCardTypeDefEntry
    MAX-ACCESS       not-accessible
    STATUS           current
    DESCRIPTION
        "Cisco Firepower equipment:IOCardTypeDef managed object table"
    ::= { cfprEquipmentObjects 72 }

cfprEquipmentIOCardTypeDefEntry OBJECT-TYPE
    SYNTAX           CfprEquipmentIOCardTypeDefEntry
    MAX-ACCESS       not-accessible
    STATUS           current
    DESCRIPTION
        "Entry for the cfprEquipmentIOCardTypeDefTable table."
    INDEX { cfprEquipmentIOCardTypeDefInstanceId }
    ::= { cfprEquipmentIOCardTypeDefTable 1 }

CfprEquipmentIOCardTypeDefEntry ::= SEQUENCE {
    cfprEquipmentIOCardTypeDefInstanceId                             CfprManagedObjectId,
    cfprEquipmentIOCardTypeDefDn                                     CfprManagedObjectDn,
    cfprEquipmentIOCardTypeDefRn                                     SnmpAdminString,
    cfprEquipmentIOCardTypeDefDescr                                  SnmpAdminString,
    cfprEquipmentIOCardTypeDefIntId                                  SnmpAdminString,
    cfprEquipmentIOCardTypeDefName                                   SnmpAdminString,
    cfprEquipmentIOCardTypeDefPolicyLevel                            Gauge32,
    cfprEquipmentIOCardTypeDefPolicyOwner                            CfprPolicyPolicyOwner,
    cfprEquipmentIOCardTypeDefType                                   SnmpAdminString
}

cfprEquipmentIOCardTypeDefInstanceId OBJECT-TYPE
    SYNTAX       CfprManagedObjectId
    MAX-ACCESS   not-accessible
    STATUS       current
    DESCRIPTION
        "Instance identifier of the managed object."
    ::= { cfprEquipmentIOCardTypeDefEntry 1 }

cfprEquipmentIOCardTypeDefDn OBJECT-TYPE
    SYNTAX       CfprManagedObjectDn
    MAX-ACCESS   read-only
    STATUS       current
    DESCRIPTION
        "Cisco Firepower equipment:IOCardTypeDef:dn managed
        object property"
    ::= { cfprEquipmentIOCardTypeDefEntry 2 }

cfprEquipmentIOCardTypeDefRn OBJECT-TYPE
    SYNTAX       SnmpAdminString
    MAX-ACCESS   read-only
    STATUS       current
    DESCRIPTION
        "Cisco Firepower equipment:IOCardTypeDef:rn managed
        object property"
    ::= { cfprEquipmentIOCardTypeDefEntry 3 }

cfprEquipmentIOCardTypeDefDescr OBJECT-TYPE
    SYNTAX       SnmpAdminString
    MAX-ACCESS   read-only
    STATUS       current
    DESCRIPTION
        "Cisco Firepower equipment:IOCardTypeDef:descr
        managed object property"
    ::= { cfprEquipmentIOCardTypeDefEntry 4 }

cfprEquipmentIOCardTypeDefIntId OBJECT-TYPE
    SYNTAX       SnmpAdminString
    MAX-ACCESS   read-only
    STATUS       current
    DESCRIPTION
        "Cisco Firepower equipment:IOCardTypeDef:intId
        managed object property"
    ::= { cfprEquipmentIOCardTypeDefEntry 5 }

cfprEquipmentIOCardTypeDefName OBJECT-TYPE
    SYNTAX       SnmpAdminString
    MAX-ACCESS   read-only
    STATUS       current
    DESCRIPTION
        "Cisco Firepower equipment:IOCardTypeDef:name managed
        object property"
    ::= { cfprEquipmentIOCardTypeDefEntry 6 }

cfprEquipmentIOCardTypeDefPolicyLevel OBJECT-TYPE
    SYNTAX       Gauge32
    MAX-ACCESS   read-only
    STATUS       current
    DESCRIPTION
        "Cisco Firepower equipment:IOCardTypeDef:policyLevel
        managed object property"
    ::= { cfprEquipmentIOCardTypeDefEntry 7 }

cfprEquipmentIOCardTypeDefPolicyOwner OBJECT-TYPE
    SYNTAX       CfprPolicyPolicyOwner
    MAX-ACCESS   read-only
    STATUS       current
    DESCRIPTION
        "Cisco Firepower equipment:IOCardTypeDef:policyOwner
        managed object property"
    ::= { cfprEquipmentIOCardTypeDefEntry 8 }

cfprEquipmentIOCardTypeDefType OBJECT-TYPE
    SYNTAX       SnmpAdminString
    MAX-ACCESS   read-only
    STATUS       current
    DESCRIPTION
        "Cisco Firepower equipment:IOCardTypeDef:type managed
        object property"
    ::= { cfprEquipmentIOCardTypeDefEntry 9 }

cfprEquipmentInbandMgmtCapTable OBJECT-TYPE
    SYNTAX           SEQUENCE OF CfprEquipmentInbandMgmtCapEntry
    MAX-ACCESS       not-accessible
    STATUS           current
    DESCRIPTION
        "Cisco Firepower equipment:InbandMgmtCap managed object table"
    ::= { cfprEquipmentObjects 73 }

cfprEquipmentInbandMgmtCapEntry OBJECT-TYPE
    SYNTAX           CfprEquipmentInbandMgmtCapEntry
    MAX-ACCESS       not-accessible
    STATUS           current
    DESCRIPTION
        "Entry for the cfprEquipmentInbandMgmtCapTable table."
    INDEX { cfprEquipmentInbandMgmtCapInstanceId }
    ::= { cfprEquipmentInbandMgmtCapTable 1 }

CfprEquipmentInbandMgmtCapEntry ::= SEQUENCE {
    cfprEquipmentInbandMgmtCapInstanceId                             CfprManagedObjectId,
    cfprEquipmentInbandMgmtCapDn                                     CfprManagedObjectDn,
    cfprEquipmentInbandMgmtCapRn                                     SnmpAdminString,
    cfprEquipmentInbandMgmtCapIsSupported                            CfprEquipmentIsSupported,
    cfprEquipmentInbandMgmtCapMinCimcVersion                         SnmpAdminString,
    cfprEquipmentInbandMgmtCapMinCmcVersion                          SnmpAdminString
}

cfprEquipmentInbandMgmtCapInstanceId OBJECT-TYPE
    SYNTAX       CfprManagedObjectId
    MAX-ACCESS   not-accessible
    STATUS       current
    DESCRIPTION
        "Instance identifier of the managed object."
    ::= { cfprEquipmentInbandMgmtCapEntry 1 }

cfprEquipmentInbandMgmtCapDn OBJECT-TYPE
    SYNTAX       CfprManagedObjectDn
    MAX-ACCESS   read-only
    STATUS       current
    DESCRIPTION
        "Cisco Firepower equipment:InbandMgmtCap:dn managed
        object property"
    ::= { cfprEquipmentInbandMgmtCapEntry 2 }

cfprEquipmentInbandMgmtCapRn OBJECT-TYPE
    SYNTAX       SnmpAdminString
    MAX-ACCESS   read-only
    STATUS       current
    DESCRIPTION
        "Cisco Firepower equipment:InbandMgmtCap:rn managed
        object property"
    ::= { cfprEquipmentInbandMgmtCapEntry 3 }

cfprEquipmentInbandMgmtCapIsSupported OBJECT-TYPE
    SYNTAX       CfprEquipmentIsSupported
    MAX-ACCESS   read-only
    STATUS       current
    DESCRIPTION
        "Cisco Firepower equipment:InbandMgmtCap:isSupported
        managed object property"
    ::= { cfprEquipmentInbandMgmtCapEntry 4 }

cfprEquipmentInbandMgmtCapMinCimcVersion OBJECT-TYPE
    SYNTAX       SnmpAdminString
    MAX-ACCESS   read-only
    STATUS       current
    DESCRIPTION
        "Cisco Firepower equipment:InbandMgmtCap:minCimcVersion
        managed object property"
    ::= { cfprEquipmentInbandMgmtCapEntry 5 }

cfprEquipmentInbandMgmtCapMinCmcVersion OBJECT-TYPE
    SYNTAX       SnmpAdminString
    MAX-ACCESS   read-only
    STATUS       current
    DESCRIPTION
        "Cisco Firepower equipment:InbandMgmtCap:minCmcVersion
        managed object property"
    ::= { cfprEquipmentInbandMgmtCapEntry 6 }

cfprEquipmentIndicatorLedTable OBJECT-TYPE
    SYNTAX           SEQUENCE OF CfprEquipmentIndicatorLedEntry
    MAX-ACCESS       not-accessible
    STATUS           current
    DESCRIPTION
        "Cisco Firepower equipment:IndicatorLed managed object table"
    ::= { cfprEquipmentObjects 74 }

cfprEquipmentIndicatorLedEntry OBJECT-TYPE
    SYNTAX           CfprEquipmentIndicatorLedEntry
    MAX-ACCESS       not-accessible
    STATUS           current
    DESCRIPTION
        "Entry for the cfprEquipmentIndicatorLedTable table."
    INDEX { cfprEquipmentIndicatorLedInstanceId }
    ::= { cfprEquipmentIndicatorLedTable 1 }

CfprEquipmentIndicatorLedEntry ::= SEQUENCE {
    cfprEquipmentIndicatorLedInstanceId                              CfprManagedObjectId,
    cfprEquipmentIndicatorLedDn                                      CfprManagedObjectDn,
    cfprEquipmentIndicatorLedRn                                      SnmpAdminString,
    cfprEquipmentIndicatorLedColor                                   CfprEquipmentLedColor,
    cfprEquipmentIndicatorLedId                                      Gauge32,
    cfprEquipmentIndicatorLedName                                    SnmpAdminString,
    cfprEquipmentIndicatorLedOperState                               CfprEquipmentLedOperState
}

cfprEquipmentIndicatorLedInstanceId OBJECT-TYPE
    SYNTAX       CfprManagedObjectId
    MAX-ACCESS   not-accessible
    STATUS       current
    DESCRIPTION
        "Instance identifier of the managed object."
    ::= { cfprEquipmentIndicatorLedEntry 1 }

cfprEquipmentIndicatorLedDn OBJECT-TYPE
    SYNTAX       CfprManagedObjectDn
    MAX-ACCESS   read-only
    STATUS       current
    DESCRIPTION
        "Cisco Firepower equipment:IndicatorLed:dn managed
        object property"
    ::= { cfprEquipmentIndicatorLedEntry 2 }

cfprEquipmentIndicatorLedRn OBJECT-TYPE
    SYNTAX       SnmpAdminString
    MAX-ACCESS   read-only
    STATUS       current
    DESCRIPTION
        "Cisco Firepower equipment:IndicatorLed:rn managed
        object property"
    ::= { cfprEquipmentIndicatorLedEntry 3 }

cfprEquipmentIndicatorLedColor OBJECT-TYPE
    SYNTAX       CfprEquipmentLedColor
    MAX-ACCESS   read-only
    STATUS       current
    DESCRIPTION
        "Cisco Firepower equipment:IndicatorLed:color managed
        object property"
    ::= { cfprEquipmentIndicatorLedEntry 4 }

cfprEquipmentIndicatorLedId OBJECT-TYPE
    SYNTAX       Gauge32
    MAX-ACCESS   read-only
    STATUS       current
    DESCRIPTION
        "Cisco Firepower equipment:IndicatorLed:id managed
        object property"
    ::= { cfprEquipmentIndicatorLedEntry 5 }

cfprEquipmentIndicatorLedName OBJECT-TYPE
    SYNTAX       SnmpAdminString
    MAX-ACCESS   read-only
    STATUS       current
    DESCRIPTION
        "Cisco Firepower equipment:IndicatorLed:name managed
        object property"
    ::= { cfprEquipmentIndicatorLedEntry 6 }

cfprEquipmentIndicatorLedOperState OBJECT-TYPE
    SYNTAX       CfprEquipmentLedOperState
    MAX-ACCESS   read-only
    STATUS       current
    DESCRIPTION
        "Cisco Firepower equipment:IndicatorLed:operState
        managed object property"
    ::= { cfprEquipmentIndicatorLedEntry 7 }

cfprEquipmentKvmMgmtCapTable OBJECT-TYPE
    SYNTAX           SEQUENCE OF CfprEquipmentKvmMgmtCapEntry
    MAX-ACCESS       not-accessible
    STATUS           current
    DESCRIPTION
        "Cisco Firepower equipment:KvmMgmtCap managed object table"
    ::= { cfprEquipmentObjects 75 }

cfprEquipmentKvmMgmtCapEntry OBJECT-TYPE
    SYNTAX           CfprEquipmentKvmMgmtCapEntry
    MAX-ACCESS       not-accessible
    STATUS           current
    DESCRIPTION
        "Entry for the cfprEquipmentKvmMgmtCapTable table."
    INDEX { cfprEquipmentKvmMgmtCapInstanceId }
    ::= { cfprEquipmentKvmMgmtCapTable 1 }

CfprEquipmentKvmMgmtCapEntry ::= SEQUENCE {
    cfprEquipmentKvmMgmtCapInstanceId                                CfprManagedObjectId,
    cfprEquipmentKvmMgmtCapDn                                        CfprManagedObjectDn,
    cfprEquipmentKvmMgmtCapRn                                        SnmpAdminString,
    cfprEquipmentKvmMgmtCapIsSupported                               CfprEquipmentIsSupported,
    cfprEquipmentKvmMgmtCapMinCimcVersion                            SnmpAdminString
}

cfprEquipmentKvmMgmtCapInstanceId OBJECT-TYPE
    SYNTAX       CfprManagedObjectId
    MAX-ACCESS   not-accessible
    STATUS       current
    DESCRIPTION
        "Instance identifier of the managed object."
    ::= { cfprEquipmentKvmMgmtCapEntry 1 }

cfprEquipmentKvmMgmtCapDn OBJECT-TYPE
    SYNTAX       CfprManagedObjectDn
    MAX-ACCESS   read-only
    STATUS       current
    DESCRIPTION
        "Cisco Firepower equipment:KvmMgmtCap:dn managed object property"
    ::= { cfprEquipmentKvmMgmtCapEntry 2 }

cfprEquipmentKvmMgmtCapRn OBJECT-TYPE
    SYNTAX       SnmpAdminString
    MAX-ACCESS   read-only
    STATUS       current
    DESCRIPTION
        "Cisco Firepower equipment:KvmMgmtCap:rn managed object property"
    ::= { cfprEquipmentKvmMgmtCapEntry 3 }

cfprEquipmentKvmMgmtCapIsSupported OBJECT-TYPE
    SYNTAX       CfprEquipmentIsSupported
    MAX-ACCESS   read-only
    STATUS       current
    DESCRIPTION
        "Cisco Firepower equipment:KvmMgmtCap:isSupported
        managed object property"
    ::= { cfprEquipmentKvmMgmtCapEntry 4 }

cfprEquipmentKvmMgmtCapMinCimcVersion OBJECT-TYPE
    SYNTAX       SnmpAdminString
    MAX-ACCESS   read-only
    STATUS       current
    DESCRIPTION
        "Cisco Firepower equipment:KvmMgmtCap:minCimcVersion
        managed object property"
    ::= { cfprEquipmentKvmMgmtCapEntry 5 }

cfprEquipmentLocalDiskCapProviderTable OBJECT-TYPE
    SYNTAX           SEQUENCE OF CfprEquipmentLocalDiskCapProviderEntry
    MAX-ACCESS       not-accessible
    STATUS           current
    DESCRIPTION
        "Cisco Firepower equipment:LocalDiskCapProvider
        managed object table"
    ::= { cfprEquipmentObjects 76 }

cfprEquipmentLocalDiskCapProviderEntry OBJECT-TYPE
    SYNTAX           CfprEquipmentLocalDiskCapProviderEntry
    MAX-ACCESS       not-accessible
    STATUS           current
    DESCRIPTION
        "Entry for the cfprEquipmentLocalDiskCapProviderTable table."
    INDEX { cfprEquipmentLocalDiskCapProviderInstanceId }
    ::= { cfprEquipmentLocalDiskCapProviderTable 1 }

CfprEquipmentLocalDiskCapProviderEntry ::= SEQUENCE {
    cfprEquipmentLocalDiskCapProviderInstanceId                      CfprManagedObjectId,
    cfprEquipmentLocalDiskCapProviderDn                              CfprManagedObjectDn,
    cfprEquipmentLocalDiskCapProviderRn                              SnmpAdminString,
    cfprEquipmentLocalDiskCapProviderDeleted                         TruthValue,
    cfprEquipmentLocalDiskCapProviderDeprecated                      TruthValue,
    cfprEquipmentLocalDiskCapProviderElementLoadFailures             Gauge32,
    cfprEquipmentLocalDiskCapProviderElementsLoaded                  Gauge32,
    cfprEquipmentLocalDiskCapProviderGencount                        Gauge32,
    cfprEquipmentLocalDiskCapProviderLoadErrors                      Gauge32,
    cfprEquipmentLocalDiskCapProviderLoadWarnings                    Gauge32,
    cfprEquipmentLocalDiskCapProviderMgmtPlaneVer                    SnmpAdminString,
    cfprEquipmentLocalDiskCapProviderModel                           SnmpAdminString,
    cfprEquipmentLocalDiskCapProviderPromCardType                    Gauge32,
    cfprEquipmentLocalDiskCapProviderRevision                        SnmpAdminString,
    cfprEquipmentLocalDiskCapProviderVendor                          SnmpAdminString
}

cfprEquipmentLocalDiskCapProviderInstanceId OBJECT-TYPE
    SYNTAX       CfprManagedObjectId
    MAX-ACCESS   not-accessible
    STATUS       current
    DESCRIPTION
        "Instance identifier of the managed object."
    ::= { cfprEquipmentLocalDiskCapProviderEntry 1 }

cfprEquipmentLocalDiskCapProviderDn OBJECT-TYPE
    SYNTAX       CfprManagedObjectDn
    MAX-ACCESS   read-only
    STATUS       current
    DESCRIPTION
        "Cisco Firepower equipment:LocalDiskCapProvider:dn
        managed object property"
    ::= { cfprEquipmentLocalDiskCapProviderEntry 2 }

cfprEquipmentLocalDiskCapProviderRn OBJECT-TYPE
    SYNTAX       SnmpAdminString
    MAX-ACCESS   read-only
    STATUS       current
    DESCRIPTION
        "Cisco Firepower equipment:LocalDiskCapProvider:rn
        managed object property"
    ::= { cfprEquipmentLocalDiskCapProviderEntry 3 }

cfprEquipmentLocalDiskCapProviderDeleted OBJECT-TYPE
    SYNTAX       TruthValue
    MAX-ACCESS   read-only
    STATUS       current
    DESCRIPTION
        "Cisco Firepower equipment:LocalDiskCapProvider:deleted
        managed object property"
    ::= { cfprEquipmentLocalDiskCapProviderEntry 4 }

cfprEquipmentLocalDiskCapProviderDeprecated OBJECT-TYPE
    SYNTAX       TruthValue
    MAX-ACCESS   read-only
    STATUS       current
    DESCRIPTION
        "Cisco Firepower equipment:LocalDiskCapProvider:deprecated
        managed object property"
    ::= { cfprEquipmentLocalDiskCapProviderEntry 5 }

cfprEquipmentLocalDiskCapProviderElementLoadFailures OBJECT-TYPE
    SYNTAX       Gauge32
    MAX-ACCESS   read-only
    STATUS       current
    DESCRIPTION
        "Cisco Firepower equipment:LocalDiskCapProvider:elementLoadFailure
        s managed object property"
    ::= { cfprEquipmentLocalDiskCapProviderEntry 6 }

cfprEquipmentLocalDiskCapProviderElementsLoaded OBJECT-TYPE
    SYNTAX       Gauge32
    MAX-ACCESS   read-only
    STATUS       current
    DESCRIPTION
        "Cisco Firepower equipment:LocalDiskCapProvider:elementsLoaded
        managed object property"
    ::= { cfprEquipmentLocalDiskCapProviderEntry 7 }

cfprEquipmentLocalDiskCapProviderGencount OBJECT-TYPE
    SYNTAX       Gauge32
    MAX-ACCESS   read-only
    STATUS       current
    DESCRIPTION
        "Cisco Firepower equipment:LocalDiskCapProvider:gencount
        managed object property"
    ::= { cfprEquipmentLocalDiskCapProviderEntry 8 }

cfprEquipmentLocalDiskCapProviderLoadErrors OBJECT-TYPE
    SYNTAX       Gauge32
    MAX-ACCESS   read-only
    STATUS       current
    DESCRIPTION
        "Cisco Firepower equipment:LocalDiskCapProvider:loadErrors
        managed object property"
    ::= { cfprEquipmentLocalDiskCapProviderEntry 9 }

cfprEquipmentLocalDiskCapProviderLoadWarnings OBJECT-TYPE
    SYNTAX       Gauge32
    MAX-ACCESS   read-only
    STATUS       current
    DESCRIPTION
        "Cisco Firepower equipment:LocalDiskCapProvider:loadWarnings
        managed object property"
    ::= { cfprEquipmentLocalDiskCapProviderEntry 10 }

cfprEquipmentLocalDiskCapProviderMgmtPlaneVer OBJECT-TYPE
    SYNTAX       SnmpAdminString
    MAX-ACCESS   read-only
    STATUS       current
    DESCRIPTION
        "Cisco Firepower equipment:LocalDiskCapProvider:mgmtPlaneVer
        managed object property"
    ::= { cfprEquipmentLocalDiskCapProviderEntry 11 }

cfprEquipmentLocalDiskCapProviderModel OBJECT-TYPE
    SYNTAX       SnmpAdminString
    MAX-ACCESS   read-only
    STATUS       current
    DESCRIPTION
        "Cisco Firepower equipment:LocalDiskCapProvider:model
        managed object property"
    ::= { cfprEquipmentLocalDiskCapProviderEntry 12 }

cfprEquipmentLocalDiskCapProviderPromCardType OBJECT-TYPE
    SYNTAX       Gauge32
    MAX-ACCESS   read-only
    STATUS       current
    DESCRIPTION
        "Cisco Firepower equipment:LocalDiskCapProvider:promCardType
        managed object property"
    ::= { cfprEquipmentLocalDiskCapProviderEntry 13 }

cfprEquipmentLocalDiskCapProviderRevision OBJECT-TYPE
    SYNTAX       SnmpAdminString
    MAX-ACCESS   read-only
    STATUS       current
    DESCRIPTION
        "Cisco Firepower equipment:LocalDiskCapProvider:revision
        managed object property"
    ::= { cfprEquipmentLocalDiskCapProviderEntry 14 }

cfprEquipmentLocalDiskCapProviderVendor OBJECT-TYPE
    SYNTAX       SnmpAdminString
    MAX-ACCESS   read-only
    STATUS       current
    DESCRIPTION
        "Cisco Firepower equipment:LocalDiskCapProvider:vendor
        managed object property"
    ::= { cfprEquipmentLocalDiskCapProviderEntry 15 }

cfprEquipmentLocalDiskControllerCapProviderTable OBJECT-TYPE
    SYNTAX           SEQUENCE OF CfprEquipmentLocalDiskControllerCapProviderEntry
    MAX-ACCESS       not-accessible
    STATUS           current
    DESCRIPTION
        "Cisco Firepower equipment:LocalDiskControllerCapProvider
        managed object table"
    ::= { cfprEquipmentObjects 77 }

cfprEquipmentLocalDiskControllerCapProviderEntry OBJECT-TYPE
    SYNTAX           CfprEquipmentLocalDiskControllerCapProviderEntry
    MAX-ACCESS       not-accessible
    STATUS           current
    DESCRIPTION
        "Entry for the cfprEquipmentLocalDiskControllerCapProviderTable table."
    INDEX { cfprEquipmentLocalDiskControllerCapProviderInstanceId }
    ::= { cfprEquipmentLocalDiskControllerCapProviderTable 1 }

CfprEquipmentLocalDiskControllerCapProviderEntry ::= SEQUENCE {
    cfprEquipmentLocalDiskControllerCapProviderInstanceId            CfprManagedObjectId,
    cfprEquipmentLocalDiskControllerCapProviderDn                    CfprManagedObjectDn,
    cfprEquipmentLocalDiskControllerCapProviderRn                    SnmpAdminString,
    cfprEquipmentLocalDiskControllerCapProviderCardType              CfprEquipmentCType,
    cfprEquipmentLocalDiskControllerCapProviderDeleted               TruthValue,
    cfprEquipmentLocalDiskControllerCapProviderDeprecated            TruthValue,
    cfprEquipmentLocalDiskControllerCapProviderElementLoadFailures   Gauge32,
    cfprEquipmentLocalDiskControllerCapProviderElementsLoaded        Gauge32,
    cfprEquipmentLocalDiskControllerCapProviderForm                  CfprStorageControllerForm,
    cfprEquipmentLocalDiskControllerCapProviderGencount              Gauge32,
    cfprEquipmentLocalDiskControllerCapProviderInternalports         Gauge32,
    cfprEquipmentLocalDiskControllerCapProviderLoadErrors            Gauge32,
    cfprEquipmentLocalDiskControllerCapProviderLoadWarnings          Gauge32,
    cfprEquipmentLocalDiskControllerCapProviderMgmtPlaneVer          SnmpAdminString,
    cfprEquipmentLocalDiskControllerCapProviderModel                 SnmpAdminString,
    cfprEquipmentLocalDiskControllerCapProviderPromCardType          Gauge32,
    cfprEquipmentLocalDiskControllerCapProviderRevision              SnmpAdminString,
    cfprEquipmentLocalDiskControllerCapProviderVendor                SnmpAdminString
}

cfprEquipmentLocalDiskControllerCapProviderInstanceId OBJECT-TYPE
    SYNTAX       CfprManagedObjectId
    MAX-ACCESS   not-accessible
    STATUS       current
    DESCRIPTION
        "Instance identifier of the managed object."
    ::= { cfprEquipmentLocalDiskControllerCapProviderEntry 1 }

cfprEquipmentLocalDiskControllerCapProviderDn OBJECT-TYPE
    SYNTAX       CfprManagedObjectDn
    MAX-ACCESS   read-only
    STATUS       current
    DESCRIPTION
        "Cisco Firepower equipment:LocalDiskControllerCapProvider:dn
        managed object property"
    ::= { cfprEquipmentLocalDiskControllerCapProviderEntry 2 }

cfprEquipmentLocalDiskControllerCapProviderRn OBJECT-TYPE
    SYNTAX       SnmpAdminString
    MAX-ACCESS   read-only
    STATUS       current
    DESCRIPTION
        "Cisco Firepower equipment:LocalDiskControllerCapProvider:rn
        managed object property"
    ::= { cfprEquipmentLocalDiskControllerCapProviderEntry 3 }

cfprEquipmentLocalDiskControllerCapProviderCardType OBJECT-TYPE
    SYNTAX       CfprEquipmentCType
    MAX-ACCESS   read-only
    STATUS       current
    DESCRIPTION
        "Cisco Firepower equipment:LocalDiskControllerCapProvider:cardType
         managed object property"
    ::= { cfprEquipmentLocalDiskControllerCapProviderEntry 4 }

cfprEquipmentLocalDiskControllerCapProviderDeleted OBJECT-TYPE
    SYNTAX       TruthValue
    MAX-ACCESS   read-only
    STATUS       current
    DESCRIPTION
        "Cisco Firepower equipment:LocalDiskControllerCapProvider:deleted
        managed object property"
    ::= { cfprEquipmentLocalDiskControllerCapProviderEntry 5 }

cfprEquipmentLocalDiskControllerCapProviderDeprecated OBJECT-TYPE
    SYNTAX       TruthValue
    MAX-ACCESS   read-only
    STATUS       current
    DESCRIPTION
        "Cisco Firepower equipment:LocalDiskControllerCapProvider:deprecat
        ed managed object property"
    ::= { cfprEquipmentLocalDiskControllerCapProviderEntry 6 }

cfprEquipmentLocalDiskControllerCapProviderElementLoadFailures OBJECT-TYPE
    SYNTAX       Gauge32
    MAX-ACCESS   read-only
    STATUS       current
    DESCRIPTION
        "Cisco Firepower equipment:LocalDiskControllerCapProvider:elementL
        oadFailures managed object property"
    ::= { cfprEquipmentLocalDiskControllerCapProviderEntry 7 }

cfprEquipmentLocalDiskControllerCapProviderElementsLoaded OBJECT-TYPE
    SYNTAX       Gauge32
    MAX-ACCESS   read-only
    STATUS       current
    DESCRIPTION
        "Cisco Firepower equipment:LocalDiskControllerCapProvider:elements
        Loaded managed object property"
    ::= { cfprEquipmentLocalDiskControllerCapProviderEntry 8 }

cfprEquipmentLocalDiskControllerCapProviderForm OBJECT-TYPE
    SYNTAX       CfprStorageControllerForm
    MAX-ACCESS   read-only
    STATUS       current
    DESCRIPTION
        "Cisco Firepower equipment:LocalDiskControllerCapProvider:form
        managed object property"
    ::= { cfprEquipmentLocalDiskControllerCapProviderEntry 9 }

cfprEquipmentLocalDiskControllerCapProviderGencount OBJECT-TYPE
    SYNTAX       Gauge32
    MAX-ACCESS   read-only
    STATUS       current
    DESCRIPTION
        "Cisco Firepower equipment:LocalDiskControllerCapProvider:gencount
         managed object property"
    ::= { cfprEquipmentLocalDiskControllerCapProviderEntry 10 }

cfprEquipmentLocalDiskControllerCapProviderInternalports OBJECT-TYPE
    SYNTAX       Gauge32
    MAX-ACCESS   read-only
    STATUS       current
    DESCRIPTION
        "Cisco Firepower equipment:LocalDiskControllerCapProvider:internal
        ports managed object property"
    ::= { cfprEquipmentLocalDiskControllerCapProviderEntry 11 }

cfprEquipmentLocalDiskControllerCapProviderLoadErrors OBJECT-TYPE
    SYNTAX       Gauge32
    MAX-ACCESS   read-only
    STATUS       current
    DESCRIPTION
        "Cisco Firepower equipment:LocalDiskControllerCapProvider:loadErro
        rs managed object property"
    ::= { cfprEquipmentLocalDiskControllerCapProviderEntry 12 }

cfprEquipmentLocalDiskControllerCapProviderLoadWarnings OBJECT-TYPE
    SYNTAX       Gauge32
    MAX-ACCESS   read-only
    STATUS       current
    DESCRIPTION
        "Cisco Firepower equipment:LocalDiskControllerCapProvider:loadWarn
        ings managed object property"
    ::= { cfprEquipmentLocalDiskControllerCapProviderEntry 13 }

cfprEquipmentLocalDiskControllerCapProviderMgmtPlaneVer OBJECT-TYPE
    SYNTAX       SnmpAdminString
    MAX-ACCESS   read-only
    STATUS       current
    DESCRIPTION
        "Cisco Firepower equipment:LocalDiskControllerCapProvider:mgmtPlan
        eVer managed object property"
    ::= { cfprEquipmentLocalDiskControllerCapProviderEntry 14 }

cfprEquipmentLocalDiskControllerCapProviderModel OBJECT-TYPE
    SYNTAX       SnmpAdminString
    MAX-ACCESS   read-only
    STATUS       current
    DESCRIPTION
        "Cisco Firepower equipment:LocalDiskControllerCapProvider:model
        managed object property"
    ::= { cfprEquipmentLocalDiskControllerCapProviderEntry 15 }

cfprEquipmentLocalDiskControllerCapProviderPromCardType OBJECT-TYPE
    SYNTAX       Gauge32
    MAX-ACCESS   read-only
    STATUS       current
    DESCRIPTION
        "Cisco Firepower equipment:LocalDiskControllerCapProvider:promCard
        Type managed object property"
    ::= { cfprEquipmentLocalDiskControllerCapProviderEntry 16 }

cfprEquipmentLocalDiskControllerCapProviderRevision OBJECT-TYPE
    SYNTAX       SnmpAdminString
    MAX-ACCESS   read-only
    STATUS       current
    DESCRIPTION
        "Cisco Firepower equipment:LocalDiskControllerCapProvider:revision
         managed object property"
    ::= { cfprEquipmentLocalDiskControllerCapProviderEntry 17 }

cfprEquipmentLocalDiskControllerCapProviderVendor OBJECT-TYPE
    SYNTAX       SnmpAdminString
    MAX-ACCESS   read-only
    STATUS       current
    DESCRIPTION
        "Cisco Firepower equipment:LocalDiskControllerCapProvider:vendor
        managed object property"
    ::= { cfprEquipmentLocalDiskControllerCapProviderEntry 18 }

cfprEquipmentLocalDiskControllerCapRefTable OBJECT-TYPE
    SYNTAX           SEQUENCE OF CfprEquipmentLocalDiskControllerCapRefEntry
    MAX-ACCESS       not-accessible
    STATUS           current
    DESCRIPTION
        "Cisco Firepower equipment:LocalDiskControllerCapRef
        managed object table"
    ::= { cfprEquipmentObjects 78 }

cfprEquipmentLocalDiskControllerCapRefEntry OBJECT-TYPE
    SYNTAX           CfprEquipmentLocalDiskControllerCapRefEntry
    MAX-ACCESS       not-accessible
    STATUS           current
    DESCRIPTION
        "Entry for the cfprEquipmentLocalDiskControllerCapRefTable table."
    INDEX { cfprEquipmentLocalDiskControllerCapRefInstanceId }
    ::= { cfprEquipmentLocalDiskControllerCapRefTable 1 }

CfprEquipmentLocalDiskControllerCapRefEntry ::= SEQUENCE {
    cfprEquipmentLocalDiskControllerCapRefInstanceId                 CfprManagedObjectId,
    cfprEquipmentLocalDiskControllerCapRefDn                         CfprManagedObjectDn,
    cfprEquipmentLocalDiskControllerCapRefRn                         SnmpAdminString,
    cfprEquipmentLocalDiskControllerCapRefIsSupported                CfprEquipmentIsSupported,
    cfprEquipmentLocalDiskControllerCapRefModel                      SnmpAdminString,
    cfprEquipmentLocalDiskControllerCapRefRevision                   SnmpAdminString,
    cfprEquipmentLocalDiskControllerCapRefVendor                     SnmpAdminString
}

cfprEquipmentLocalDiskControllerCapRefInstanceId OBJECT-TYPE
    SYNTAX       CfprManagedObjectId
    MAX-ACCESS   not-accessible
    STATUS       current
    DESCRIPTION
        "Instance identifier of the managed object."
    ::= { cfprEquipmentLocalDiskControllerCapRefEntry 1 }

cfprEquipmentLocalDiskControllerCapRefDn OBJECT-TYPE
    SYNTAX       CfprManagedObjectDn
    MAX-ACCESS   read-only
    STATUS       current
    DESCRIPTION
        "Cisco Firepower equipment:LocalDiskControllerCapRef:dn
        managed object property"
    ::= { cfprEquipmentLocalDiskControllerCapRefEntry 2 }

cfprEquipmentLocalDiskControllerCapRefRn OBJECT-TYPE
    SYNTAX       SnmpAdminString
    MAX-ACCESS   read-only
    STATUS       current
    DESCRIPTION
        "Cisco Firepower equipment:LocalDiskControllerCapRef:rn
        managed object property"
    ::= { cfprEquipmentLocalDiskControllerCapRefEntry 3 }

cfprEquipmentLocalDiskControllerCapRefIsSupported OBJECT-TYPE
    SYNTAX       CfprEquipmentIsSupported
    MAX-ACCESS   read-only
    STATUS       current
    DESCRIPTION
        "Cisco Firepower equipment:LocalDiskControllerCapRef:isSupported
        managed object property"
    ::= { cfprEquipmentLocalDiskControllerCapRefEntry 4 }

cfprEquipmentLocalDiskControllerCapRefModel OBJECT-TYPE
    SYNTAX       SnmpAdminString
    MAX-ACCESS   read-only
    STATUS       current
    DESCRIPTION
        "Cisco Firepower equipment:LocalDiskControllerCapRef:model
        managed object property"
    ::= { cfprEquipmentLocalDiskControllerCapRefEntry 5 }

cfprEquipmentLocalDiskControllerCapRefRevision OBJECT-TYPE
    SYNTAX       SnmpAdminString
    MAX-ACCESS   read-only
    STATUS       current
    DESCRIPTION
        "Cisco Firepower equipment:LocalDiskControllerCapRef:revision
        managed object property"
    ::= { cfprEquipmentLocalDiskControllerCapRefEntry 6 }

cfprEquipmentLocalDiskControllerCapRefVendor OBJECT-TYPE
    SYNTAX       SnmpAdminString
    MAX-ACCESS   read-only
    STATUS       current
    DESCRIPTION
        "Cisco Firepower equipment:LocalDiskControllerCapRef:vendor
        managed object property"
    ::= { cfprEquipmentLocalDiskControllerCapRefEntry 7 }

cfprEquipmentLocalDiskControllerDefTable OBJECT-TYPE
    SYNTAX           SEQUENCE OF CfprEquipmentLocalDiskControllerDefEntry
    MAX-ACCESS       not-accessible
    STATUS           current
    DESCRIPTION
        "Cisco Firepower equipment:LocalDiskControllerDef
        managed object table"
    ::= { cfprEquipmentObjects 79 }

cfprEquipmentLocalDiskControllerDefEntry OBJECT-TYPE
    SYNTAX           CfprEquipmentLocalDiskControllerDefEntry
    MAX-ACCESS       not-accessible
    STATUS           current
    DESCRIPTION
        "Entry for the cfprEquipmentLocalDiskControllerDefTable table."
    INDEX { cfprEquipmentLocalDiskControllerDefInstanceId }
    ::= { cfprEquipmentLocalDiskControllerDefTable 1 }

CfprEquipmentLocalDiskControllerDefEntry ::= SEQUENCE {
    cfprEquipmentLocalDiskControllerDefInstanceId                    CfprManagedObjectId,
    cfprEquipmentLocalDiskControllerDefDn                            CfprManagedObjectDn,
    cfprEquipmentLocalDiskControllerDefRn                            SnmpAdminString,
    cfprEquipmentLocalDiskControllerDefDescr                         SnmpAdminString,
    cfprEquipmentLocalDiskControllerDefForceUpdateVersion            TruthValue,
    cfprEquipmentLocalDiskControllerDefIntId                         SnmpAdminString,
    cfprEquipmentLocalDiskControllerDefName                          SnmpAdminString,
    cfprEquipmentLocalDiskControllerDefPolicyLevel                   Gauge32,
    cfprEquipmentLocalDiskControllerDefPolicyOwner                   CfprPolicyPolicyOwner
}

cfprEquipmentLocalDiskControllerDefInstanceId OBJECT-TYPE
    SYNTAX       CfprManagedObjectId
    MAX-ACCESS   not-accessible
    STATUS       current
    DESCRIPTION
        "Instance identifier of the managed object."
    ::= { cfprEquipmentLocalDiskControllerDefEntry 1 }

cfprEquipmentLocalDiskControllerDefDn OBJECT-TYPE
    SYNTAX       CfprManagedObjectDn
    MAX-ACCESS   read-only
    STATUS       current
    DESCRIPTION
        "Cisco Firepower equipment:LocalDiskControllerDef:dn
        managed object property"
    ::= { cfprEquipmentLocalDiskControllerDefEntry 2 }

cfprEquipmentLocalDiskControllerDefRn OBJECT-TYPE
    SYNTAX       SnmpAdminString
    MAX-ACCESS   read-only
    STATUS       current
    DESCRIPTION
        "Cisco Firepower equipment:LocalDiskControllerDef:rn
        managed object property"
    ::= { cfprEquipmentLocalDiskControllerDefEntry 3 }

cfprEquipmentLocalDiskControllerDefDescr OBJECT-TYPE
    SYNTAX       SnmpAdminString
    MAX-ACCESS   read-only
    STATUS       current
    DESCRIPTION
        "Cisco Firepower equipment:LocalDiskControllerDef:descr
        managed object property"
    ::= { cfprEquipmentLocalDiskControllerDefEntry 4 }

cfprEquipmentLocalDiskControllerDefForceUpdateVersion OBJECT-TYPE
    SYNTAX       TruthValue
    MAX-ACCESS   read-only
    STATUS       current
    DESCRIPTION
        "Cisco Firepower equipment:LocalDiskControllerDef:forceUpdateVersi
        on managed object property"
    ::= { cfprEquipmentLocalDiskControllerDefEntry 5 }

cfprEquipmentLocalDiskControllerDefIntId OBJECT-TYPE
    SYNTAX       SnmpAdminString
    MAX-ACCESS   read-only
    STATUS       current
    DESCRIPTION
        "Cisco Firepower equipment:LocalDiskControllerDef:intId
        managed object property"
    ::= { cfprEquipmentLocalDiskControllerDefEntry 6 }

cfprEquipmentLocalDiskControllerDefName OBJECT-TYPE
    SYNTAX       SnmpAdminString
    MAX-ACCESS   read-only
    STATUS       current
    DESCRIPTION
        "Cisco Firepower equipment:LocalDiskControllerDef:name
        managed object property"
    ::= { cfprEquipmentLocalDiskControllerDefEntry 7 }

cfprEquipmentLocalDiskControllerDefPolicyLevel OBJECT-TYPE
    SYNTAX       Gauge32
    MAX-ACCESS   read-only
    STATUS       current
    DESCRIPTION
        "Cisco Firepower equipment:LocalDiskControllerDef:policyLevel
        managed object property"
    ::= { cfprEquipmentLocalDiskControllerDefEntry 8 }

cfprEquipmentLocalDiskControllerDefPolicyOwner OBJECT-TYPE
    SYNTAX       CfprPolicyPolicyOwner
    MAX-ACCESS   read-only
    STATUS       current
    DESCRIPTION
        "Cisco Firepower equipment:LocalDiskControllerDef:policyOwner
        managed object property"
    ::= { cfprEquipmentLocalDiskControllerDefEntry 9 }

cfprEquipmentLocalDiskDefTable OBJECT-TYPE
    SYNTAX           SEQUENCE OF CfprEquipmentLocalDiskDefEntry
    MAX-ACCESS       not-accessible
    STATUS           current
    DESCRIPTION
        "Cisco Firepower equipment:LocalDiskDef managed object table"
    ::= { cfprEquipmentObjects 80 }

cfprEquipmentLocalDiskDefEntry OBJECT-TYPE
    SYNTAX           CfprEquipmentLocalDiskDefEntry
    MAX-ACCESS       not-accessible
    STATUS           current
    DESCRIPTION
        "Entry for the cfprEquipmentLocalDiskDefTable table."
    INDEX { cfprEquipmentLocalDiskDefInstanceId }
    ::= { cfprEquipmentLocalDiskDefTable 1 }

CfprEquipmentLocalDiskDefEntry ::= SEQUENCE {
    cfprEquipmentLocalDiskDefInstanceId                              CfprManagedObjectId,
    cfprEquipmentLocalDiskDefDn                                      CfprManagedObjectDn,
    cfprEquipmentLocalDiskDefRn                                      SnmpAdminString,
    cfprEquipmentLocalDiskDefBlockSize                               Gauge32,
    cfprEquipmentLocalDiskDefCacheSize                               SnmpAdminString,
    cfprEquipmentLocalDiskDefCapacity                                SnmpAdminString,
    cfprEquipmentLocalDiskDefDescr                                   SnmpAdminString,
    cfprEquipmentLocalDiskDefForceUpdateVersion                      TruthValue,
    cfprEquipmentLocalDiskDefIntId                                   SnmpAdminString,
    cfprEquipmentLocalDiskDefLinkSpeed                               SnmpAdminString,
    cfprEquipmentLocalDiskDefName                                    SnmpAdminString,
    cfprEquipmentLocalDiskDefNumberOfBlocks                          Unsigned64,
    cfprEquipmentLocalDiskDefPolicyLevel                             Gauge32,
    cfprEquipmentLocalDiskDefPolicyOwner                             CfprPolicyPolicyOwner,
    cfprEquipmentLocalDiskDefRotationalSpeed                         INTEGER,
    cfprEquipmentLocalDiskDefSeekAverageReadWrite                    SnmpAdminString,
    cfprEquipmentLocalDiskDefSeekTrackToTrackReadWrite               SnmpAdminString,
    cfprEquipmentLocalDiskDefTechnology                              CfprStorageTechnology
}

cfprEquipmentLocalDiskDefInstanceId OBJECT-TYPE
    SYNTAX       CfprManagedObjectId
    MAX-ACCESS   not-accessible
    STATUS       current
    DESCRIPTION
        "Instance identifier of the managed object."
    ::= { cfprEquipmentLocalDiskDefEntry 1 }

cfprEquipmentLocalDiskDefDn OBJECT-TYPE
    SYNTAX       CfprManagedObjectDn
    MAX-ACCESS   read-only
    STATUS       current
    DESCRIPTION
        "Cisco Firepower equipment:LocalDiskDef:dn managed
        object property"
    ::= { cfprEquipmentLocalDiskDefEntry 2 }

cfprEquipmentLocalDiskDefRn OBJECT-TYPE
    SYNTAX       SnmpAdminString
    MAX-ACCESS   read-only
    STATUS       current
    DESCRIPTION
        "Cisco Firepower equipment:LocalDiskDef:rn managed
        object property"
    ::= { cfprEquipmentLocalDiskDefEntry 3 }

cfprEquipmentLocalDiskDefBlockSize OBJECT-TYPE
    SYNTAX       Gauge32
    MAX-ACCESS   read-only
    STATUS       current
    DESCRIPTION
        "Cisco Firepower equipment:LocalDiskDef:blockSize
        managed object property"
    ::= { cfprEquipmentLocalDiskDefEntry 4 }

cfprEquipmentLocalDiskDefCacheSize OBJECT-TYPE
    SYNTAX       SnmpAdminString
    MAX-ACCESS   read-only
    STATUS       current
    DESCRIPTION
        "Cisco Firepower equipment:LocalDiskDef:cacheSize
        managed object property"
    ::= { cfprEquipmentLocalDiskDefEntry 5 }

cfprEquipmentLocalDiskDefCapacity OBJECT-TYPE
    SYNTAX       SnmpAdminString
    MAX-ACCESS   read-only
    STATUS       current
    DESCRIPTION
        "Cisco Firepower equipment:LocalDiskDef:capacity
        managed object property"
    ::= { cfprEquipmentLocalDiskDefEntry 6 }

cfprEquipmentLocalDiskDefDescr OBJECT-TYPE
    SYNTAX       SnmpAdminString
    MAX-ACCESS   read-only
    STATUS       current
    DESCRIPTION
        "Cisco Firepower equipment:LocalDiskDef:descr managed
        object property"
    ::= { cfprEquipmentLocalDiskDefEntry 7 }

cfprEquipmentLocalDiskDefForceUpdateVersion OBJECT-TYPE
    SYNTAX       TruthValue
    MAX-ACCESS   read-only
    STATUS       current
    DESCRIPTION
        "Cisco Firepower equipment:LocalDiskDef:forceUpdateVersion
        managed object property"
    ::= { cfprEquipmentLocalDiskDefEntry 8 }

cfprEquipmentLocalDiskDefIntId OBJECT-TYPE
    SYNTAX       SnmpAdminString
    MAX-ACCESS   read-only
    STATUS       current
    DESCRIPTION
        "Cisco Firepower equipment:LocalDiskDef:intId managed
        object property"
    ::= { cfprEquipmentLocalDiskDefEntry 9 }

cfprEquipmentLocalDiskDefLinkSpeed OBJECT-TYPE
    SYNTAX       SnmpAdminString
    MAX-ACCESS   read-only
    STATUS       current
    DESCRIPTION
        "Cisco Firepower equipment:LocalDiskDef:linkSpeed
        managed object property"
    ::= { cfprEquipmentLocalDiskDefEntry 10 }

cfprEquipmentLocalDiskDefName OBJECT-TYPE
    SYNTAX       SnmpAdminString
    MAX-ACCESS   read-only
    STATUS       current
    DESCRIPTION
        "Cisco Firepower equipment:LocalDiskDef:name managed
        object property"
    ::= { cfprEquipmentLocalDiskDefEntry 11 }

cfprEquipmentLocalDiskDefNumberOfBlocks OBJECT-TYPE
    SYNTAX       Unsigned64
    MAX-ACCESS   read-only
    STATUS       current
    DESCRIPTION
        "Cisco Firepower equipment:LocalDiskDef:numberOfBlocks
        managed object property"
    ::= { cfprEquipmentLocalDiskDefEntry 12 }

cfprEquipmentLocalDiskDefPolicyLevel OBJECT-TYPE
    SYNTAX       Gauge32
    MAX-ACCESS   read-only
    STATUS       current
    DESCRIPTION
        "Cisco Firepower equipment:LocalDiskDef:policyLevel
        managed object property"
    ::= { cfprEquipmentLocalDiskDefEntry 13 }

cfprEquipmentLocalDiskDefPolicyOwner OBJECT-TYPE
    SYNTAX       CfprPolicyPolicyOwner
    MAX-ACCESS   read-only
    STATUS       current
    DESCRIPTION
        "Cisco Firepower equipment:LocalDiskDef:policyOwner
        managed object property"
    ::= { cfprEquipmentLocalDiskDefEntry 14 }

cfprEquipmentLocalDiskDefRotationalSpeed OBJECT-TYPE
    SYNTAX       INTEGER
    MAX-ACCESS   read-only
    STATUS       current
    DESCRIPTION
        "Cisco Firepower equipment:LocalDiskDef:rotationalSpeed
        managed object property"
    ::= { cfprEquipmentLocalDiskDefEntry 15 }

cfprEquipmentLocalDiskDefSeekAverageReadWrite OBJECT-TYPE
    SYNTAX       SnmpAdminString
    MAX-ACCESS   read-only
    STATUS       current
    DESCRIPTION
        "Cisco Firepower equipment:LocalDiskDef:seekAverageReadWrite
        managed object property"
    ::= { cfprEquipmentLocalDiskDefEntry 16 }

cfprEquipmentLocalDiskDefSeekTrackToTrackReadWrite OBJECT-TYPE
    SYNTAX       SnmpAdminString
    MAX-ACCESS   read-only
    STATUS       current
    DESCRIPTION
        "Cisco Firepower equipment:LocalDiskDef:seekTrackToTrackReadWrite
        managed object property"
    ::= { cfprEquipmentLocalDiskDefEntry 17 }

cfprEquipmentLocalDiskDefTechnology OBJECT-TYPE
    SYNTAX       CfprStorageTechnology
    MAX-ACCESS   read-only
    STATUS       current
    DESCRIPTION
        "Cisco Firepower equipment:LocalDiskDef:technology
        managed object property"
    ::= { cfprEquipmentLocalDiskDefEntry 18 }

cfprEquipmentLocatorLedTable OBJECT-TYPE
    SYNTAX           SEQUENCE OF CfprEquipmentLocatorLedEntry
    MAX-ACCESS       not-accessible
    STATUS           current
    DESCRIPTION
        "Cisco Firepower equipment:LocatorLed managed object table"
    ::= { cfprEquipmentObjects 81 }

cfprEquipmentLocatorLedEntry OBJECT-TYPE
    SYNTAX           CfprEquipmentLocatorLedEntry
    MAX-ACCESS       not-accessible
    STATUS           current
    DESCRIPTION
        "Entry for the cfprEquipmentLocatorLedTable table."
    INDEX { cfprEquipmentLocatorLedInstanceId }
    ::= { cfprEquipmentLocatorLedTable 1 }

CfprEquipmentLocatorLedEntry ::= SEQUENCE {
    cfprEquipmentLocatorLedInstanceId                                CfprManagedObjectId,
    cfprEquipmentLocatorLedDn                                        CfprManagedObjectDn,
    cfprEquipmentLocatorLedRn                                        SnmpAdminString,
    cfprEquipmentLocatorLedAdminState                                CfprEquipmentLedLocatorState,
    cfprEquipmentLocatorLedBoardType                                 CfprEquipmentBoardAggregationRole,
    cfprEquipmentLocatorLedColor                                     CfprEquipmentLedColor,
    cfprEquipmentLocatorLedFsmDescr                                  SnmpAdminString,
    cfprEquipmentLocatorLedFsmPrev                                   SnmpAdminString,
    cfprEquipmentLocatorLedFsmProgr                                  Gauge32,
    cfprEquipmentLocatorLedFsmRmtInvErrCode                          Gauge32,
    cfprEquipmentLocatorLedFsmRmtInvErrDescr                         SnmpAdminString,
    cfprEquipmentLocatorLedFsmRmtInvRslt                             CfprConditionRemoteInvRslt,
    cfprEquipmentLocatorLedFsmStageDescr                             SnmpAdminString,
    cfprEquipmentLocatorLedFsmStamp                                  DateAndTime,
    cfprEquipmentLocatorLedFsmStatus                                 SnmpAdminString,
    cfprEquipmentLocatorLedFsmTry                                    Gauge32,
    cfprEquipmentLocatorLedId                                        Gauge32,
    cfprEquipmentLocatorLedName                                      SnmpAdminString,
    cfprEquipmentLocatorLedOperState                                 CfprEquipmentLedOperState
}

cfprEquipmentLocatorLedInstanceId OBJECT-TYPE
    SYNTAX       CfprManagedObjectId
    MAX-ACCESS   not-accessible
    STATUS       current
    DESCRIPTION
        "Instance identifier of the managed object."
    ::= { cfprEquipmentLocatorLedEntry 1 }

cfprEquipmentLocatorLedDn OBJECT-TYPE
    SYNTAX       CfprManagedObjectDn
    MAX-ACCESS   read-only
    STATUS       current
    DESCRIPTION
        "Cisco Firepower equipment:LocatorLed:dn managed object property"
    ::= { cfprEquipmentLocatorLedEntry 2 }

cfprEquipmentLocatorLedRn OBJECT-TYPE
    SYNTAX       SnmpAdminString
    MAX-ACCESS   read-only
    STATUS       current
    DESCRIPTION
        "Cisco Firepower equipment:LocatorLed:rn managed object property"
    ::= { cfprEquipmentLocatorLedEntry 3 }

cfprEquipmentLocatorLedAdminState OBJECT-TYPE
    SYNTAX       CfprEquipmentLedLocatorState
    MAX-ACCESS   read-only
    STATUS       current
    DESCRIPTION
        "Cisco Firepower equipment:LocatorLed:adminState
        managed object property"
    ::= { cfprEquipmentLocatorLedEntry 4 }

cfprEquipmentLocatorLedBoardType OBJECT-TYPE
    SYNTAX       CfprEquipmentBoardAggregationRole
    MAX-ACCESS   read-only
    STATUS       current
    DESCRIPTION
        "Cisco Firepower equipment:LocatorLed:boardType
        managed object property"
    ::= { cfprEquipmentLocatorLedEntry 5 }

cfprEquipmentLocatorLedColor OBJECT-TYPE
    SYNTAX       CfprEquipmentLedColor
    MAX-ACCESS   read-only
    STATUS       current
    DESCRIPTION
        "Cisco Firepower equipment:LocatorLed:color managed
        object property"
    ::= { cfprEquipmentLocatorLedEntry 6 }

cfprEquipmentLocatorLedFsmDescr OBJECT-TYPE
    SYNTAX       SnmpAdminString
    MAX-ACCESS   read-only
    STATUS       current
    DESCRIPTION
        "Cisco Firepower equipment:LocatorLed:fsmDescr
        managed object property"
    ::= { cfprEquipmentLocatorLedEntry 7 }

cfprEquipmentLocatorLedFsmPrev OBJECT-TYPE
    SYNTAX       SnmpAdminString
    MAX-ACCESS   read-only
    STATUS       current
    DESCRIPTION
        "Cisco Firepower equipment:LocatorLed:fsmPrev managed
        object property"
    ::= { cfprEquipmentLocatorLedEntry 8 }

cfprEquipmentLocatorLedFsmProgr OBJECT-TYPE
    SYNTAX       Gauge32
    MAX-ACCESS   read-only
    STATUS       current
    DESCRIPTION
        "Cisco Firepower equipment:LocatorLed:fsmProgr
        managed object property"
    ::= { cfprEquipmentLocatorLedEntry 9 }

cfprEquipmentLocatorLedFsmRmtInvErrCode OBJECT-TYPE
    SYNTAX       Gauge32
    MAX-ACCESS   read-only
    STATUS       current
    DESCRIPTION
        "Cisco Firepower equipment:LocatorLed:fsmRmtInvErrCode
        managed object property"
    ::= { cfprEquipmentLocatorLedEntry 10 }

cfprEquipmentLocatorLedFsmRmtInvErrDescr OBJECT-TYPE
    SYNTAX       SnmpAdminString
    MAX-ACCESS   read-only
    STATUS       current
    DESCRIPTION
        "Cisco Firepower equipment:LocatorLed:fsmRmtInvErrDescr
        managed object property"
    ::= { cfprEquipmentLocatorLedEntry 11 }

cfprEquipmentLocatorLedFsmRmtInvRslt OBJECT-TYPE
    SYNTAX       CfprConditionRemoteInvRslt
    MAX-ACCESS   read-only
    STATUS       current
    DESCRIPTION
        "Cisco Firepower equipment:LocatorLed:fsmRmtInvRslt
        managed object property"
    ::= { cfprEquipmentLocatorLedEntry 12 }

cfprEquipmentLocatorLedFsmStageDescr OBJECT-TYPE
    SYNTAX       SnmpAdminString
    MAX-ACCESS   read-only
    STATUS       current
    DESCRIPTION
        "Cisco Firepower equipment:LocatorLed:fsmStageDescr
        managed object property"
    ::= { cfprEquipmentLocatorLedEntry 13 }

cfprEquipmentLocatorLedFsmStamp OBJECT-TYPE
    SYNTAX       DateAndTime
    MAX-ACCESS   read-only
    STATUS       current
    DESCRIPTION
        "Cisco Firepower equipment:LocatorLed:fsmStamp
        managed object property"
    ::= { cfprEquipmentLocatorLedEntry 14 }

cfprEquipmentLocatorLedFsmStatus OBJECT-TYPE
    SYNTAX       SnmpAdminString
    MAX-ACCESS   read-only
    STATUS       current
    DESCRIPTION
        "Cisco Firepower equipment:LocatorLed:fsmStatus
        managed object property"
    ::= { cfprEquipmentLocatorLedEntry 15 }

cfprEquipmentLocatorLedFsmTry OBJECT-TYPE
    SYNTAX       Gauge32
    MAX-ACCESS   read-only
    STATUS       current
    DESCRIPTION
        "Cisco Firepower equipment:LocatorLed:fsmTry managed
        object property"
    ::= { cfprEquipmentLocatorLedEntry 16 }

cfprEquipmentLocatorLedId OBJECT-TYPE
    SYNTAX       Gauge32
    MAX-ACCESS   read-only
    STATUS       current
    DESCRIPTION
        "Cisco Firepower equipment:LocatorLed:id managed object property"
    ::= { cfprEquipmentLocatorLedEntry 17 }

cfprEquipmentLocatorLedName OBJECT-TYPE
    SYNTAX       SnmpAdminString
    MAX-ACCESS   read-only
    STATUS       current
    DESCRIPTION
        "Cisco Firepower equipment:LocatorLed:name managed
        object property"
    ::= { cfprEquipmentLocatorLedEntry 18 }

cfprEquipmentLocatorLedOperState OBJECT-TYPE
    SYNTAX       CfprEquipmentLedOperState
    MAX-ACCESS   read-only
    STATUS       current
    DESCRIPTION
        "Cisco Firepower equipment:LocatorLed:operState
        managed object property"
    ::= { cfprEquipmentLocatorLedEntry 19 }

cfprEquipmentLocatorLedFsmTable OBJECT-TYPE
    SYNTAX           SEQUENCE OF CfprEquipmentLocatorLedFsmEntry
    MAX-ACCESS       not-accessible
    STATUS           current
    DESCRIPTION
        "Cisco Firepower equipment:LocatorLedFsm managed object table"
    ::= { cfprEquipmentObjects 82 }

cfprEquipmentLocatorLedFsmEntry OBJECT-TYPE
    SYNTAX           CfprEquipmentLocatorLedFsmEntry
    MAX-ACCESS       not-accessible
    STATUS           current
    DESCRIPTION
        "Entry for the cfprEquipmentLocatorLedFsmTable table."
    INDEX { cfprEquipmentLocatorLedFsmInstanceId }
    ::= { cfprEquipmentLocatorLedFsmTable 1 }

CfprEquipmentLocatorLedFsmEntry ::= SEQUENCE {
    cfprEquipmentLocatorLedFsmInstanceId                             CfprManagedObjectId,
    cfprEquipmentLocatorLedFsmDn                                     CfprManagedObjectDn,
    cfprEquipmentLocatorLedFsmRn                                     SnmpAdminString,
    cfprEquipmentLocatorLedFsmCompletionTime                         DateAndTime,
    cfprEquipmentLocatorLedFsmCurrentFsm                             CfprEquipmentLocatorLedFsmCurrentFsm,
    cfprEquipmentLocatorLedFsmDescrData                              SnmpAdminString,
    cfprEquipmentLocatorLedFsmFsmStatus                              CfprFsmFsmStageStatus,
    cfprEquipmentLocatorLedFsmProgress                               Gauge32,
    cfprEquipmentLocatorLedFsmRmtErrCode                             Gauge32,
    cfprEquipmentLocatorLedFsmRmtErrDescr                            SnmpAdminString,
    cfprEquipmentLocatorLedFsmRmtRslt                                CfprConditionRemoteInvRslt
}

cfprEquipmentLocatorLedFsmInstanceId OBJECT-TYPE
    SYNTAX       CfprManagedObjectId
    MAX-ACCESS   not-accessible
    STATUS       current
    DESCRIPTION
        "Instance identifier of the managed object."
    ::= { cfprEquipmentLocatorLedFsmEntry 1 }

cfprEquipmentLocatorLedFsmDn OBJECT-TYPE
    SYNTAX       CfprManagedObjectDn
    MAX-ACCESS   read-only
    STATUS       current
    DESCRIPTION
        "Cisco Firepower equipment:LocatorLedFsm:dn managed
        object property"
    ::= { cfprEquipmentLocatorLedFsmEntry 2 }

cfprEquipmentLocatorLedFsmRn OBJECT-TYPE
    SYNTAX       SnmpAdminString
    MAX-ACCESS   read-only
    STATUS       current
    DESCRIPTION
        "Cisco Firepower equipment:LocatorLedFsm:rn managed
        object property"
    ::= { cfprEquipmentLocatorLedFsmEntry 3 }

cfprEquipmentLocatorLedFsmCompletionTime OBJECT-TYPE
    SYNTAX       DateAndTime
    MAX-ACCESS   read-only
    STATUS       current
    DESCRIPTION
        "Cisco Firepower equipment:LocatorLedFsm:completionTime
        managed object property"
    ::= { cfprEquipmentLocatorLedFsmEntry 4 }

cfprEquipmentLocatorLedFsmCurrentFsm OBJECT-TYPE
    SYNTAX       CfprEquipmentLocatorLedFsmCurrentFsm
    MAX-ACCESS   read-only
    STATUS       current
    DESCRIPTION
        "Cisco Firepower equipment:LocatorLedFsm:currentFsm
        managed object property"
    ::= { cfprEquipmentLocatorLedFsmEntry 5 }

cfprEquipmentLocatorLedFsmDescrData OBJECT-TYPE
    SYNTAX       SnmpAdminString
    MAX-ACCESS   read-only
    STATUS       current
    DESCRIPTION
        "Cisco Firepower equipment:LocatorLedFsm:descr
        managed object property"
    ::= { cfprEquipmentLocatorLedFsmEntry 6 }

cfprEquipmentLocatorLedFsmFsmStatus OBJECT-TYPE
    SYNTAX       CfprFsmFsmStageStatus
    MAX-ACCESS   read-only
    STATUS       current
    DESCRIPTION
        "Cisco Firepower equipment:LocatorLedFsm:fsmStatus
        managed object property"
    ::= { cfprEquipmentLocatorLedFsmEntry 7 }

cfprEquipmentLocatorLedFsmProgress OBJECT-TYPE
    SYNTAX       Gauge32
    MAX-ACCESS   read-only
    STATUS       current
    DESCRIPTION
        "Cisco Firepower equipment:LocatorLedFsm:progress
        managed object property"
    ::= { cfprEquipmentLocatorLedFsmEntry 8 }

cfprEquipmentLocatorLedFsmRmtErrCode OBJECT-TYPE
    SYNTAX       Gauge32
    MAX-ACCESS   read-only
    STATUS       current
    DESCRIPTION
        "Cisco Firepower equipment:LocatorLedFsm:rmtErrCode
        managed object property"
    ::= { cfprEquipmentLocatorLedFsmEntry 9 }

cfprEquipmentLocatorLedFsmRmtErrDescr OBJECT-TYPE
    SYNTAX       SnmpAdminString
    MAX-ACCESS   read-only
    STATUS       current
    DESCRIPTION
        "Cisco Firepower equipment:LocatorLedFsm:rmtErrDescr
        managed object property"
    ::= { cfprEquipmentLocatorLedFsmEntry 10 }

cfprEquipmentLocatorLedFsmRmtRslt OBJECT-TYPE
    SYNTAX       CfprConditionRemoteInvRslt
    MAX-ACCESS   read-only
    STATUS       current
    DESCRIPTION
        "Cisco Firepower equipment:LocatorLedFsm:rmtRslt
        managed object property"
    ::= { cfprEquipmentLocatorLedFsmEntry 11 }

cfprEquipmentLocatorLedFsmStageTable OBJECT-TYPE
    SYNTAX           SEQUENCE OF CfprEquipmentLocatorLedFsmStageEntry
    MAX-ACCESS       not-accessible
    STATUS           current
    DESCRIPTION
        "Cisco Firepower equipment:LocatorLedFsmStage managed
        object table"
    ::= { cfprEquipmentObjects 83 }

cfprEquipmentLocatorLedFsmStageEntry OBJECT-TYPE
    SYNTAX           CfprEquipmentLocatorLedFsmStageEntry
    MAX-ACCESS       not-accessible
    STATUS           current
    DESCRIPTION
        "Entry for the cfprEquipmentLocatorLedFsmStageTable table."
    INDEX { cfprEquipmentLocatorLedFsmStageInstanceId }
    ::= { cfprEquipmentLocatorLedFsmStageTable 1 }

CfprEquipmentLocatorLedFsmStageEntry ::= SEQUENCE {
    cfprEquipmentLocatorLedFsmStageInstanceId                        CfprManagedObjectId,
    cfprEquipmentLocatorLedFsmStageDn                                CfprManagedObjectDn,
    cfprEquipmentLocatorLedFsmStageRn                                SnmpAdminString,
    cfprEquipmentLocatorLedFsmStageDescrData                         SnmpAdminString,
    cfprEquipmentLocatorLedFsmStageLastUpdateTime                    DateAndTime,
    cfprEquipmentLocatorLedFsmStageName                              CfprEquipmentLocatorLedFsmStageName,
    cfprEquipmentLocatorLedFsmStageOrder                             Gauge32,
    cfprEquipmentLocatorLedFsmStageRetry                             Gauge32,
    cfprEquipmentLocatorLedFsmStageStageStatus                       CfprFsmFsmStageStatus
}

cfprEquipmentLocatorLedFsmStageInstanceId OBJECT-TYPE
    SYNTAX       CfprManagedObjectId
    MAX-ACCESS   not-accessible
    STATUS       current
    DESCRIPTION
        "Instance identifier of the managed object."
    ::= { cfprEquipmentLocatorLedFsmStageEntry 1 }

cfprEquipmentLocatorLedFsmStageDn OBJECT-TYPE
    SYNTAX       CfprManagedObjectDn
    MAX-ACCESS   read-only
    STATUS       current
    DESCRIPTION
        "Cisco Firepower equipment:LocatorLedFsmStage:dn
        managed object property"
    ::= { cfprEquipmentLocatorLedFsmStageEntry 2 }

cfprEquipmentLocatorLedFsmStageRn OBJECT-TYPE
    SYNTAX       SnmpAdminString
    MAX-ACCESS   read-only
    STATUS       current
    DESCRIPTION
        "Cisco Firepower equipment:LocatorLedFsmStage:rn
        managed object property"
    ::= { cfprEquipmentLocatorLedFsmStageEntry 3 }

cfprEquipmentLocatorLedFsmStageDescrData OBJECT-TYPE
    SYNTAX       SnmpAdminString
    MAX-ACCESS   read-only
    STATUS       current
    DESCRIPTION
        "Cisco Firepower equipment:LocatorLedFsmStage:descr
        managed object property"
    ::= { cfprEquipmentLocatorLedFsmStageEntry 4 }

cfprEquipmentLocatorLedFsmStageLastUpdateTime OBJECT-TYPE
    SYNTAX       DateAndTime
    MAX-ACCESS   read-only
    STATUS       current
    DESCRIPTION
        "Cisco Firepower equipment:LocatorLedFsmStage:lastUpdateTime
        managed object property"
    ::= { cfprEquipmentLocatorLedFsmStageEntry 5 }

cfprEquipmentLocatorLedFsmStageName OBJECT-TYPE
    SYNTAX       CfprEquipmentLocatorLedFsmStageName
    MAX-ACCESS   read-only
    STATUS       current
    DESCRIPTION
        "Cisco Firepower equipment:LocatorLedFsmStage:name
        managed object property"
    ::= { cfprEquipmentLocatorLedFsmStageEntry 6 }

cfprEquipmentLocatorLedFsmStageOrder OBJECT-TYPE
    SYNTAX       Gauge32
    MAX-ACCESS   read-only
    STATUS       current
    DESCRIPTION
        "Cisco Firepower equipment:LocatorLedFsmStage:order
        managed object property"
    ::= { cfprEquipmentLocatorLedFsmStageEntry 7 }

cfprEquipmentLocatorLedFsmStageRetry OBJECT-TYPE
    SYNTAX       Gauge32
    MAX-ACCESS   read-only
    STATUS       current
    DESCRIPTION
        "Cisco Firepower equipment:LocatorLedFsmStage:retry
        managed object property"
    ::= { cfprEquipmentLocatorLedFsmStageEntry 8 }

cfprEquipmentLocatorLedFsmStageStageStatus OBJECT-TYPE
    SYNTAX       CfprFsmFsmStageStatus
    MAX-ACCESS   read-only
    STATUS       current
    DESCRIPTION
        "Cisco Firepower equipment:LocatorLedFsmStage:stageStatus
        managed object property"
    ::= { cfprEquipmentLocatorLedFsmStageEntry 9 }

cfprEquipmentLocatorLedFsmTaskTable OBJECT-TYPE
    SYNTAX           SEQUENCE OF CfprEquipmentLocatorLedFsmTaskEntry
    MAX-ACCESS       not-accessible
    STATUS           current
    DESCRIPTION
        "Cisco Firepower equipment:LocatorLedFsmTask managed object table"
    ::= { cfprEquipmentObjects 84 }

cfprEquipmentLocatorLedFsmTaskEntry OBJECT-TYPE
    SYNTAX           CfprEquipmentLocatorLedFsmTaskEntry
    MAX-ACCESS       not-accessible
    STATUS           current
    DESCRIPTION
        "Entry for the cfprEquipmentLocatorLedFsmTaskTable table."
    INDEX { cfprEquipmentLocatorLedFsmTaskInstanceId }
    ::= { cfprEquipmentLocatorLedFsmTaskTable 1 }

CfprEquipmentLocatorLedFsmTaskEntry ::= SEQUENCE {
    cfprEquipmentLocatorLedFsmTaskInstanceId                         CfprManagedObjectId,
    cfprEquipmentLocatorLedFsmTaskDn                                 CfprManagedObjectDn,
    cfprEquipmentLocatorLedFsmTaskRn                                 SnmpAdminString,
    cfprEquipmentLocatorLedFsmTaskCompletion                         CfprFsmCompletion,
    cfprEquipmentLocatorLedFsmTaskFlags                              CfprFsmFlags,
    cfprEquipmentLocatorLedFsmTaskItem                               CfprEquipmentLocatorLedFsmTaskItem,
    cfprEquipmentLocatorLedFsmTaskSeqId                              Gauge32
}

cfprEquipmentLocatorLedFsmTaskInstanceId OBJECT-TYPE
    SYNTAX       CfprManagedObjectId
    MAX-ACCESS   not-accessible
    STATUS       current
    DESCRIPTION
        "Instance identifier of the managed object."
    ::= { cfprEquipmentLocatorLedFsmTaskEntry 1 }

cfprEquipmentLocatorLedFsmTaskDn OBJECT-TYPE
    SYNTAX       CfprManagedObjectDn
    MAX-ACCESS   read-only
    STATUS       current
    DESCRIPTION
        "Cisco Firepower equipment:LocatorLedFsmTask:dn
        managed object property"
    ::= { cfprEquipmentLocatorLedFsmTaskEntry 2 }

cfprEquipmentLocatorLedFsmTaskRn OBJECT-TYPE
    SYNTAX       SnmpAdminString
    MAX-ACCESS   read-only
    STATUS       current
    DESCRIPTION
        "Cisco Firepower equipment:LocatorLedFsmTask:rn
        managed object property"
    ::= { cfprEquipmentLocatorLedFsmTaskEntry 3 }

cfprEquipmentLocatorLedFsmTaskCompletion OBJECT-TYPE
    SYNTAX       CfprFsmCompletion
    MAX-ACCESS   read-only
    STATUS       current
    DESCRIPTION
        "Cisco Firepower equipment:LocatorLedFsmTask:completion
        managed object property"
    ::= { cfprEquipmentLocatorLedFsmTaskEntry 4 }

cfprEquipmentLocatorLedFsmTaskFlags OBJECT-TYPE
    SYNTAX       CfprFsmFlags
    MAX-ACCESS   read-only
    STATUS       current
    DESCRIPTION
        "Cisco Firepower equipment:LocatorLedFsmTask:flags
        managed object property"
    ::= { cfprEquipmentLocatorLedFsmTaskEntry 5 }

cfprEquipmentLocatorLedFsmTaskItem OBJECT-TYPE
    SYNTAX       CfprEquipmentLocatorLedFsmTaskItem
    MAX-ACCESS   read-only
    STATUS       current
    DESCRIPTION
        "Cisco Firepower equipment:LocatorLedFsmTask:item
        managed object property"
    ::= { cfprEquipmentLocatorLedFsmTaskEntry 6 }

cfprEquipmentLocatorLedFsmTaskSeqId OBJECT-TYPE
    SYNTAX       Gauge32
    MAX-ACCESS   read-only
    STATUS       current
    DESCRIPTION
        "Cisco Firepower equipment:LocatorLedFsmTask:seqId
        managed object property"
    ::= { cfprEquipmentLocatorLedFsmTaskEntry 7 }

cfprEquipmentManufacturingDefTable OBJECT-TYPE
    SYNTAX           SEQUENCE OF CfprEquipmentManufacturingDefEntry
    MAX-ACCESS       not-accessible
    STATUS           current
    DESCRIPTION
        "Cisco Firepower equipment:ManufacturingDef managed object table"
    ::= { cfprEquipmentObjects 85 }

cfprEquipmentManufacturingDefEntry OBJECT-TYPE
    SYNTAX           CfprEquipmentManufacturingDefEntry
    MAX-ACCESS       not-accessible
    STATUS           current
    DESCRIPTION
        "Entry for the cfprEquipmentManufacturingDefTable table."
    INDEX { cfprEquipmentManufacturingDefInstanceId }
    ::= { cfprEquipmentManufacturingDefTable 1 }

CfprEquipmentManufacturingDefEntry ::= SEQUENCE {
    cfprEquipmentManufacturingDefInstanceId                          CfprManagedObjectId,
    cfprEquipmentManufacturingDefDn                                  CfprManagedObjectDn,
    cfprEquipmentManufacturingDefRn                                  SnmpAdminString,
    cfprEquipmentManufacturingDefCaption                             SnmpAdminString,
    cfprEquipmentManufacturingDefClei                                SnmpAdminString,
    cfprEquipmentManufacturingDefDescr                               SnmpAdminString,
    cfprEquipmentManufacturingDefDescription                         SnmpAdminString,
    cfprEquipmentManufacturingDefFruMajorType                        SnmpAdminString,
    cfprEquipmentManufacturingDefFruMinorType                        SnmpAdminString,
    cfprEquipmentManufacturingDefIntId                               SnmpAdminString,
    cfprEquipmentManufacturingDefName                                SnmpAdminString,
    cfprEquipmentManufacturingDefOemName                             SnmpAdminString,
    cfprEquipmentManufacturingDefOemPartNumber                       SnmpAdminString,
    cfprEquipmentManufacturingDefPartNumber                          SnmpAdminString,
    cfprEquipmentManufacturingDefPid                                 SnmpAdminString,
    cfprEquipmentManufacturingDefPolicyLevel                         Gauge32,
    cfprEquipmentManufacturingDefPolicyOwner                         CfprPolicyPolicyOwner,
    cfprEquipmentManufacturingDefSeries                              SnmpAdminString,
    cfprEquipmentManufacturingDefSku                                 SnmpAdminString,
    cfprEquipmentManufacturingDefVendorEquipmentType                 SnmpAdminString,
    cfprEquipmentManufacturingDefVid                                 SnmpAdminString,
    cfprEquipmentManufacturingDefInstalledPhyMemorySize              Gauge32
}

cfprEquipmentManufacturingDefInstanceId OBJECT-TYPE
    SYNTAX       CfprManagedObjectId
    MAX-ACCESS   not-accessible
    STATUS       current
    DESCRIPTION
        "Instance identifier of the managed object."
    ::= { cfprEquipmentManufacturingDefEntry 1 }

cfprEquipmentManufacturingDefDn OBJECT-TYPE
    SYNTAX       CfprManagedObjectDn
    MAX-ACCESS   read-only
    STATUS       current
    DESCRIPTION
        "Cisco Firepower equipment:ManufacturingDef:dn
        managed object property"
    ::= { cfprEquipmentManufacturingDefEntry 2 }

cfprEquipmentManufacturingDefRn OBJECT-TYPE
    SYNTAX       SnmpAdminString
    MAX-ACCESS   read-only
    STATUS       current
    DESCRIPTION
        "Cisco Firepower equipment:ManufacturingDef:rn
        managed object property"
    ::= { cfprEquipmentManufacturingDefEntry 3 }

cfprEquipmentManufacturingDefCaption OBJECT-TYPE
    SYNTAX       SnmpAdminString
    MAX-ACCESS   read-only
    STATUS       current
    DESCRIPTION
        "Cisco Firepower equipment:ManufacturingDef:caption
        managed object property"
    ::= { cfprEquipmentManufacturingDefEntry 4 }

cfprEquipmentManufacturingDefClei OBJECT-TYPE
    SYNTAX       SnmpAdminString
    MAX-ACCESS   read-only
    STATUS       current
    DESCRIPTION
        "Cisco Firepower equipment:ManufacturingDef:clei
        managed object property"
    ::= { cfprEquipmentManufacturingDefEntry 5 }

cfprEquipmentManufacturingDefDescr OBJECT-TYPE
    SYNTAX       SnmpAdminString
    MAX-ACCESS   read-only
    STATUS       current
    DESCRIPTION
        "Cisco Firepower equipment:ManufacturingDef:descr
        managed object property"
    ::= { cfprEquipmentManufacturingDefEntry 6 }

cfprEquipmentManufacturingDefDescription OBJECT-TYPE
    SYNTAX       SnmpAdminString
    MAX-ACCESS   read-only
    STATUS       current
    DESCRIPTION
        "Cisco Firepower equipment:ManufacturingDef:description
        managed object property"
    ::= { cfprEquipmentManufacturingDefEntry 7 }

cfprEquipmentManufacturingDefFruMajorType OBJECT-TYPE
    SYNTAX       SnmpAdminString
    MAX-ACCESS   read-only
    STATUS       current
    DESCRIPTION
        "Cisco Firepower equipment:ManufacturingDef:fruMajorType
        managed object property"
    ::= { cfprEquipmentManufacturingDefEntry 8 }

cfprEquipmentManufacturingDefFruMinorType OBJECT-TYPE
    SYNTAX       SnmpAdminString
    MAX-ACCESS   read-only
    STATUS       current
    DESCRIPTION
        "Cisco Firepower equipment:ManufacturingDef:fruMinorType
        managed object property"
    ::= { cfprEquipmentManufacturingDefEntry 9 }

cfprEquipmentManufacturingDefIntId OBJECT-TYPE
    SYNTAX       SnmpAdminString
    MAX-ACCESS   read-only
    STATUS       current
    DESCRIPTION
        "Cisco Firepower equipment:ManufacturingDef:intId
        managed object property"
    ::= { cfprEquipmentManufacturingDefEntry 10 }

cfprEquipmentManufacturingDefName OBJECT-TYPE
    SYNTAX       SnmpAdminString
    MAX-ACCESS   read-only
    STATUS       current
    DESCRIPTION
        "Cisco Firepower equipment:ManufacturingDef:name
        managed object property"
    ::= { cfprEquipmentManufacturingDefEntry 11 }

cfprEquipmentManufacturingDefOemName OBJECT-TYPE
    SYNTAX       SnmpAdminString
    MAX-ACCESS   read-only
    STATUS       current
    DESCRIPTION
        "Cisco Firepower equipment:ManufacturingDef:oemName
        managed object property"
    ::= { cfprEquipmentManufacturingDefEntry 12 }

cfprEquipmentManufacturingDefOemPartNumber OBJECT-TYPE
    SYNTAX       SnmpAdminString
    MAX-ACCESS   read-only
    STATUS       current
    DESCRIPTION
        "Cisco Firepower equipment:ManufacturingDef:oemPartNumber
        managed object property"
    ::= { cfprEquipmentManufacturingDefEntry 13 }

cfprEquipmentManufacturingDefPartNumber OBJECT-TYPE
    SYNTAX       SnmpAdminString
    MAX-ACCESS   read-only
    STATUS       current
    DESCRIPTION
        "Cisco Firepower equipment:ManufacturingDef:partNumber
        managed object property"
    ::= { cfprEquipmentManufacturingDefEntry 14 }

cfprEquipmentManufacturingDefPid OBJECT-TYPE
    SYNTAX       SnmpAdminString
    MAX-ACCESS   read-only
    STATUS       current
    DESCRIPTION
        "Cisco Firepower equipment:ManufacturingDef:pid
        managed object property"
    ::= { cfprEquipmentManufacturingDefEntry 15 }

cfprEquipmentManufacturingDefPolicyLevel OBJECT-TYPE
    SYNTAX       Gauge32
    MAX-ACCESS   read-only
    STATUS       current
    DESCRIPTION
        "Cisco Firepower equipment:ManufacturingDef:policyLevel
        managed object property"
    ::= { cfprEquipmentManufacturingDefEntry 16 }

cfprEquipmentManufacturingDefPolicyOwner OBJECT-TYPE
    SYNTAX       CfprPolicyPolicyOwner
    MAX-ACCESS   read-only
    STATUS       current
    DESCRIPTION
        "Cisco Firepower equipment:ManufacturingDef:policyOwner
        managed object property"
    ::= { cfprEquipmentManufacturingDefEntry 17 }

cfprEquipmentManufacturingDefSeries OBJECT-TYPE
    SYNTAX       SnmpAdminString
    MAX-ACCESS   read-only
    STATUS       current
    DESCRIPTION
        "Cisco Firepower equipment:ManufacturingDef:series
        managed object property"
    ::= { cfprEquipmentManufacturingDefEntry 18 }

cfprEquipmentManufacturingDefSku OBJECT-TYPE
    SYNTAX       SnmpAdminString
    MAX-ACCESS   read-only
    STATUS       current
    DESCRIPTION
        "Cisco Firepower equipment:ManufacturingDef:sku
        managed object property"
    ::= { cfprEquipmentManufacturingDefEntry 19 }

cfprEquipmentManufacturingDefVendorEquipmentType OBJECT-TYPE
    SYNTAX       SnmpAdminString
    MAX-ACCESS   read-only
    STATUS       current
    DESCRIPTION
        "Cisco Firepower equipment:ManufacturingDef:vendorEquipmentType
        managed object property"
    ::= { cfprEquipmentManufacturingDefEntry 20 }

cfprEquipmentManufacturingDefVid OBJECT-TYPE
    SYNTAX       SnmpAdminString
    MAX-ACCESS   read-only
    STATUS       current
    DESCRIPTION
        "Cisco Firepower equipment:ManufacturingDef:vid
        managed object property"
    ::= { cfprEquipmentManufacturingDefEntry 21 }

cfprEquipmentManufacturingDefInstalledPhyMemorySize OBJECT-TYPE
    SYNTAX       Gauge32
    MAX-ACCESS   read-only
    STATUS       current
    DESCRIPTION
        "Cisco Firepower equipment:ManufacturingDef:installedPhyMemorySize
         managed object property"
    ::= { cfprEquipmentManufacturingDefEntry 22 }

cfprEquipmentMaxPortSpeedCapProviderTable OBJECT-TYPE
    SYNTAX           SEQUENCE OF CfprEquipmentMaxPortSpeedCapProviderEntry
    MAX-ACCESS       not-accessible
    STATUS           current
    DESCRIPTION
        "Cisco Firepower equipment:MaxPortSpeedCapProvider
        managed object table"
    ::= { cfprEquipmentObjects 86 }

cfprEquipmentMaxPortSpeedCapProviderEntry OBJECT-TYPE
    SYNTAX           CfprEquipmentMaxPortSpeedCapProviderEntry
    MAX-ACCESS       not-accessible
    STATUS           current
    DESCRIPTION
        "Entry for the cfprEquipmentMaxPortSpeedCapProviderTable table."
    INDEX { cfprEquipmentMaxPortSpeedCapProviderInstanceId }
    ::= { cfprEquipmentMaxPortSpeedCapProviderTable 1 }

CfprEquipmentMaxPortSpeedCapProviderEntry ::= SEQUENCE {
    cfprEquipmentMaxPortSpeedCapProviderInstanceId                   CfprManagedObjectId,
    cfprEquipmentMaxPortSpeedCapProviderDn                           CfprManagedObjectDn,
    cfprEquipmentMaxPortSpeedCapProviderRn                           SnmpAdminString,
    cfprEquipmentMaxPortSpeedCapProviderDescr                        SnmpAdminString,
    cfprEquipmentMaxPortSpeedCapProviderEndPortId                    Gauge32,
    cfprEquipmentMaxPortSpeedCapProviderIntId                        SnmpAdminString,
    cfprEquipmentMaxPortSpeedCapProviderName                         SnmpAdminString,
    cfprEquipmentMaxPortSpeedCapProviderPolicyLevel                  Gauge32,
    cfprEquipmentMaxPortSpeedCapProviderPolicyOwner                  CfprPolicyPolicyOwner,
    cfprEquipmentMaxPortSpeedCapProviderStartPortId                  Gauge32,
    cfprEquipmentMaxPortSpeedCapProviderSupportedSpeed               Unsigned64
}

cfprEquipmentMaxPortSpeedCapProviderInstanceId OBJECT-TYPE
    SYNTAX       CfprManagedObjectId
    MAX-ACCESS   not-accessible
    STATUS       current
    DESCRIPTION
        "Instance identifier of the managed object."
    ::= { cfprEquipmentMaxPortSpeedCapProviderEntry 1 }

cfprEquipmentMaxPortSpeedCapProviderDn OBJECT-TYPE
    SYNTAX       CfprManagedObjectDn
    MAX-ACCESS   read-only
    STATUS       current
    DESCRIPTION
        "Cisco Firepower equipment:MaxPortSpeedCapProvider:dn
        managed object property"
    ::= { cfprEquipmentMaxPortSpeedCapProviderEntry 2 }

cfprEquipmentMaxPortSpeedCapProviderRn OBJECT-TYPE
    SYNTAX       SnmpAdminString
    MAX-ACCESS   read-only
    STATUS       current
    DESCRIPTION
        "Cisco Firepower equipment:MaxPortSpeedCapProvider:rn
        managed object property"
    ::= { cfprEquipmentMaxPortSpeedCapProviderEntry 3 }

cfprEquipmentMaxPortSpeedCapProviderDescr OBJECT-TYPE
    SYNTAX       SnmpAdminString
    MAX-ACCESS   read-only
    STATUS       current
    DESCRIPTION
        "Cisco Firepower equipment:MaxPortSpeedCapProvider:descr
        managed object property"
    ::= { cfprEquipmentMaxPortSpeedCapProviderEntry 4 }

cfprEquipmentMaxPortSpeedCapProviderEndPortId OBJECT-TYPE
    SYNTAX       Gauge32
    MAX-ACCESS   read-only
    STATUS       current
    DESCRIPTION
        "Cisco Firepower equipment:MaxPortSpeedCapProvider:endPortId
        managed object property"
    ::= { cfprEquipmentMaxPortSpeedCapProviderEntry 5 }

cfprEquipmentMaxPortSpeedCapProviderIntId OBJECT-TYPE
    SYNTAX       SnmpAdminString
    MAX-ACCESS   read-only
    STATUS       current
    DESCRIPTION
        "Cisco Firepower equipment:MaxPortSpeedCapProvider:intId
        managed object property"
    ::= { cfprEquipmentMaxPortSpeedCapProviderEntry 6 }

cfprEquipmentMaxPortSpeedCapProviderName OBJECT-TYPE
    SYNTAX       SnmpAdminString
    MAX-ACCESS   read-only
    STATUS       current
    DESCRIPTION
        "Cisco Firepower equipment:MaxPortSpeedCapProvider:name
        managed object property"
    ::= { cfprEquipmentMaxPortSpeedCapProviderEntry 7 }

cfprEquipmentMaxPortSpeedCapProviderPolicyLevel OBJECT-TYPE
    SYNTAX       Gauge32
    MAX-ACCESS   read-only
    STATUS       current
    DESCRIPTION
        "Cisco Firepower equipment:MaxPortSpeedCapProvider:policyLevel
        managed object property"
    ::= { cfprEquipmentMaxPortSpeedCapProviderEntry 8 }

cfprEquipmentMaxPortSpeedCapProviderPolicyOwner OBJECT-TYPE
    SYNTAX       CfprPolicyPolicyOwner
    MAX-ACCESS   read-only
    STATUS       current
    DESCRIPTION
        "Cisco Firepower equipment:MaxPortSpeedCapProvider:policyOwner
        managed object property"
    ::= { cfprEquipmentMaxPortSpeedCapProviderEntry 9 }

cfprEquipmentMaxPortSpeedCapProviderStartPortId OBJECT-TYPE
    SYNTAX       Gauge32
    MAX-ACCESS   read-only
    STATUS       current
    DESCRIPTION
        "Cisco Firepower equipment:MaxPortSpeedCapProvider:startPortId
        managed object property"
    ::= { cfprEquipmentMaxPortSpeedCapProviderEntry 10 }

cfprEquipmentMaxPortSpeedCapProviderSupportedSpeed OBJECT-TYPE
    SYNTAX       Unsigned64
    MAX-ACCESS   read-only
    STATUS       current
    DESCRIPTION
        "Cisco Firepower equipment:MaxPortSpeedCapProvider:supportedSpeed
        managed object property"
    ::= { cfprEquipmentMaxPortSpeedCapProviderEntry 11 }

cfprEquipmentMemoryUnitCapProviderTable OBJECT-TYPE
    SYNTAX           SEQUENCE OF CfprEquipmentMemoryUnitCapProviderEntry
    MAX-ACCESS       not-accessible
    STATUS           current
    DESCRIPTION
        "Cisco Firepower equipment:MemoryUnitCapProvider
        managed object table"
    ::= { cfprEquipmentObjects 87 }

cfprEquipmentMemoryUnitCapProviderEntry OBJECT-TYPE
    SYNTAX           CfprEquipmentMemoryUnitCapProviderEntry
    MAX-ACCESS       not-accessible
    STATUS           current
    DESCRIPTION
        "Entry for the cfprEquipmentMemoryUnitCapProviderTable table."
    INDEX { cfprEquipmentMemoryUnitCapProviderInstanceId }
    ::= { cfprEquipmentMemoryUnitCapProviderTable 1 }

CfprEquipmentMemoryUnitCapProviderEntry ::= SEQUENCE {
    cfprEquipmentMemoryUnitCapProviderInstanceId                     CfprManagedObjectId,
    cfprEquipmentMemoryUnitCapProviderDn                             CfprManagedObjectDn,
    cfprEquipmentMemoryUnitCapProviderRn                             SnmpAdminString,
    cfprEquipmentMemoryUnitCapProviderDeleted                        TruthValue,
    cfprEquipmentMemoryUnitCapProviderDeprecated                     TruthValue,
    cfprEquipmentMemoryUnitCapProviderElementLoadFailures            Gauge32,
    cfprEquipmentMemoryUnitCapProviderElementsLoaded                 Gauge32,
    cfprEquipmentMemoryUnitCapProviderGencount                       Gauge32,
    cfprEquipmentMemoryUnitCapProviderLoadErrors                     Gauge32,
    cfprEquipmentMemoryUnitCapProviderLoadWarnings                   Gauge32,
    cfprEquipmentMemoryUnitCapProviderMgmtPlaneVer                   SnmpAdminString,
    cfprEquipmentMemoryUnitCapProviderModel                          SnmpAdminString,
    cfprEquipmentMemoryUnitCapProviderPromCardType                   Gauge32,
    cfprEquipmentMemoryUnitCapProviderRevision                       SnmpAdminString,
    cfprEquipmentMemoryUnitCapProviderVendor                         SnmpAdminString
}

cfprEquipmentMemoryUnitCapProviderInstanceId OBJECT-TYPE
    SYNTAX       CfprManagedObjectId
    MAX-ACCESS   not-accessible
    STATUS       current
    DESCRIPTION
        "Instance identifier of the managed object."
    ::= { cfprEquipmentMemoryUnitCapProviderEntry 1 }

cfprEquipmentMemoryUnitCapProviderDn OBJECT-TYPE
    SYNTAX       CfprManagedObjectDn
    MAX-ACCESS   read-only
    STATUS       current
    DESCRIPTION
        "Cisco Firepower equipment:MemoryUnitCapProvider:dn
        managed object property"
    ::= { cfprEquipmentMemoryUnitCapProviderEntry 2 }

cfprEquipmentMemoryUnitCapProviderRn OBJECT-TYPE
    SYNTAX       SnmpAdminString
    MAX-ACCESS   read-only
    STATUS       current
    DESCRIPTION
        "Cisco Firepower equipment:MemoryUnitCapProvider:rn
        managed object property"
    ::= { cfprEquipmentMemoryUnitCapProviderEntry 3 }

cfprEquipmentMemoryUnitCapProviderDeleted OBJECT-TYPE
    SYNTAX       TruthValue
    MAX-ACCESS   read-only
    STATUS       current
    DESCRIPTION
        "Cisco Firepower equipment:MemoryUnitCapProvider:deleted
        managed object property"
    ::= { cfprEquipmentMemoryUnitCapProviderEntry 4 }

cfprEquipmentMemoryUnitCapProviderDeprecated OBJECT-TYPE
    SYNTAX       TruthValue
    MAX-ACCESS   read-only
    STATUS       current
    DESCRIPTION
        "Cisco Firepower equipment:MemoryUnitCapProvider:deprecated
        managed object property"
    ::= { cfprEquipmentMemoryUnitCapProviderEntry 5 }

cfprEquipmentMemoryUnitCapProviderElementLoadFailures OBJECT-TYPE
    SYNTAX       Gauge32
    MAX-ACCESS   read-only
    STATUS       current
    DESCRIPTION
        "Cisco Firepower equipment:MemoryUnitCapProvider:elementLoadFailur
        es managed object property"
    ::= { cfprEquipmentMemoryUnitCapProviderEntry 6 }

cfprEquipmentMemoryUnitCapProviderElementsLoaded OBJECT-TYPE
    SYNTAX       Gauge32
    MAX-ACCESS   read-only
    STATUS       current
    DESCRIPTION
        "Cisco Firepower equipment:MemoryUnitCapProvider:elementsLoaded
        managed object property"
    ::= { cfprEquipmentMemoryUnitCapProviderEntry 7 }

cfprEquipmentMemoryUnitCapProviderGencount OBJECT-TYPE
    SYNTAX       Gauge32
    MAX-ACCESS   read-only
    STATUS       current
    DESCRIPTION
        "Cisco Firepower equipment:MemoryUnitCapProvider:gencount
        managed object property"
    ::= { cfprEquipmentMemoryUnitCapProviderEntry 8 }

cfprEquipmentMemoryUnitCapProviderLoadErrors OBJECT-TYPE
    SYNTAX       Gauge32
    MAX-ACCESS   read-only
    STATUS       current
    DESCRIPTION
        "Cisco Firepower equipment:MemoryUnitCapProvider:loadErrors
        managed object property"
    ::= { cfprEquipmentMemoryUnitCapProviderEntry 9 }

cfprEquipmentMemoryUnitCapProviderLoadWarnings OBJECT-TYPE
    SYNTAX       Gauge32
    MAX-ACCESS   read-only
    STATUS       current
    DESCRIPTION
        "Cisco Firepower equipment:MemoryUnitCapProvider:loadWarnings
        managed object property"
    ::= { cfprEquipmentMemoryUnitCapProviderEntry 10 }

cfprEquipmentMemoryUnitCapProviderMgmtPlaneVer OBJECT-TYPE
    SYNTAX       SnmpAdminString
    MAX-ACCESS   read-only
    STATUS       current
    DESCRIPTION
        "Cisco Firepower equipment:MemoryUnitCapProvider:mgmtPlaneVer
        managed object property"
    ::= { cfprEquipmentMemoryUnitCapProviderEntry 11 }

cfprEquipmentMemoryUnitCapProviderModel OBJECT-TYPE
    SYNTAX       SnmpAdminString
    MAX-ACCESS   read-only
    STATUS       current
    DESCRIPTION
        "Cisco Firepower equipment:MemoryUnitCapProvider:model
        managed object property"
    ::= { cfprEquipmentMemoryUnitCapProviderEntry 12 }

cfprEquipmentMemoryUnitCapProviderPromCardType OBJECT-TYPE
    SYNTAX       Gauge32
    MAX-ACCESS   read-only
    STATUS       current
    DESCRIPTION
        "Cisco Firepower equipment:MemoryUnitCapProvider:promCardType
        managed object property"
    ::= { cfprEquipmentMemoryUnitCapProviderEntry 13 }

cfprEquipmentMemoryUnitCapProviderRevision OBJECT-TYPE
    SYNTAX       SnmpAdminString
    MAX-ACCESS   read-only
    STATUS       current
    DESCRIPTION
        "Cisco Firepower equipment:MemoryUnitCapProvider:revision
        managed object property"
    ::= { cfprEquipmentMemoryUnitCapProviderEntry 14 }

cfprEquipmentMemoryUnitCapProviderVendor OBJECT-TYPE
    SYNTAX       SnmpAdminString
    MAX-ACCESS   read-only
    STATUS       current
    DESCRIPTION
        "Cisco Firepower equipment:MemoryUnitCapProvider:vendor
        managed object property"
    ::= { cfprEquipmentMemoryUnitCapProviderEntry 15 }

cfprEquipmentMemoryUnitDiscoveryModifierDefTable OBJECT-TYPE
    SYNTAX           SEQUENCE OF CfprEquipmentMemoryUnitDiscoveryModifierDefEntry
    MAX-ACCESS       not-accessible
    STATUS           current
    DESCRIPTION
        "Cisco Firepower equipment:MemoryUnitDiscoveryModifierDef
        managed object table"
    ::= { cfprEquipmentObjects 88 }

cfprEquipmentMemoryUnitDiscoveryModifierDefEntry OBJECT-TYPE
    SYNTAX           CfprEquipmentMemoryUnitDiscoveryModifierDefEntry
    MAX-ACCESS       not-accessible
    STATUS           current
    DESCRIPTION
        "Entry for the cfprEquipmentMemoryUnitDiscoveryModifierDefTable table."
    INDEX { cfprEquipmentMemoryUnitDiscoveryModifierDefInstanceId }
    ::= { cfprEquipmentMemoryUnitDiscoveryModifierDefTable 1 }

CfprEquipmentMemoryUnitDiscoveryModifierDefEntry ::= SEQUENCE {
    cfprEquipmentMemoryUnitDiscoveryModifierDefInstanceId            CfprManagedObjectId,
    cfprEquipmentMemoryUnitDiscoveryModifierDefDn                    CfprManagedObjectDn,
    cfprEquipmentMemoryUnitDiscoveryModifierDefRn                    SnmpAdminString,
    cfprEquipmentMemoryUnitDiscoveryModifierDefAction                CfprEquipmentMemoryUnitDiscoveryModifierAction,
    cfprEquipmentMemoryUnitDiscoveryModifierDefConstraintType        CfprComputeMemoryUnitConstraintType,
    cfprEquipmentMemoryUnitDiscoveryModifierDefDescr                 SnmpAdminString,
    cfprEquipmentMemoryUnitDiscoveryModifierDefIntId                 SnmpAdminString,
    cfprEquipmentMemoryUnitDiscoveryModifierDefName                  SnmpAdminString,
    cfprEquipmentMemoryUnitDiscoveryModifierDefPolicyLevel           Gauge32,
    cfprEquipmentMemoryUnitDiscoveryModifierDefPolicyOwner           CfprPolicyPolicyOwner
}

cfprEquipmentMemoryUnitDiscoveryModifierDefInstanceId OBJECT-TYPE
    SYNTAX       CfprManagedObjectId
    MAX-ACCESS   not-accessible
    STATUS       current
    DESCRIPTION
        "Instance identifier of the managed object."
    ::= { cfprEquipmentMemoryUnitDiscoveryModifierDefEntry 1 }

cfprEquipmentMemoryUnitDiscoveryModifierDefDn OBJECT-TYPE
    SYNTAX       CfprManagedObjectDn
    MAX-ACCESS   read-only
    STATUS       current
    DESCRIPTION
        "Cisco Firepower equipment:MemoryUnitDiscoveryModifierDef:dn
        managed object property"
    ::= { cfprEquipmentMemoryUnitDiscoveryModifierDefEntry 2 }

cfprEquipmentMemoryUnitDiscoveryModifierDefRn OBJECT-TYPE
    SYNTAX       SnmpAdminString
    MAX-ACCESS   read-only
    STATUS       current
    DESCRIPTION
        "Cisco Firepower equipment:MemoryUnitDiscoveryModifierDef:rn
        managed object property"
    ::= { cfprEquipmentMemoryUnitDiscoveryModifierDefEntry 3 }

cfprEquipmentMemoryUnitDiscoveryModifierDefAction OBJECT-TYPE
    SYNTAX       CfprEquipmentMemoryUnitDiscoveryModifierAction
    MAX-ACCESS   read-only
    STATUS       current
    DESCRIPTION
        "Cisco Firepower equipment:MemoryUnitDiscoveryModifierDef:action
        managed object property"
    ::= { cfprEquipmentMemoryUnitDiscoveryModifierDefEntry 4 }

cfprEquipmentMemoryUnitDiscoveryModifierDefConstraintType OBJECT-TYPE
    SYNTAX       CfprComputeMemoryUnitConstraintType
    MAX-ACCESS   read-only
    STATUS       current
    DESCRIPTION
        "Cisco Firepower equipment:MemoryUnitDiscoveryModifierDef:constrai
        ntType managed object property"
    ::= { cfprEquipmentMemoryUnitDiscoveryModifierDefEntry 5 }

cfprEquipmentMemoryUnitDiscoveryModifierDefDescr OBJECT-TYPE
    SYNTAX       SnmpAdminString
    MAX-ACCESS   read-only
    STATUS       current
    DESCRIPTION
        "Cisco Firepower equipment:MemoryUnitDiscoveryModifierDef:descr
        managed object property"
    ::= { cfprEquipmentMemoryUnitDiscoveryModifierDefEntry 6 }

cfprEquipmentMemoryUnitDiscoveryModifierDefIntId OBJECT-TYPE
    SYNTAX       SnmpAdminString
    MAX-ACCESS   read-only
    STATUS       current
    DESCRIPTION
        "Cisco Firepower equipment:MemoryUnitDiscoveryModifierDef:intId
        managed object property"
    ::= { cfprEquipmentMemoryUnitDiscoveryModifierDefEntry 7 }

cfprEquipmentMemoryUnitDiscoveryModifierDefName OBJECT-TYPE
    SYNTAX       SnmpAdminString
    MAX-ACCESS   read-only
    STATUS       current
    DESCRIPTION
        "Cisco Firepower equipment:MemoryUnitDiscoveryModifierDef:name
        managed object property"
    ::= { cfprEquipmentMemoryUnitDiscoveryModifierDefEntry 8 }

cfprEquipmentMemoryUnitDiscoveryModifierDefPolicyLevel OBJECT-TYPE
    SYNTAX       Gauge32
    MAX-ACCESS   read-only
    STATUS       current
    DESCRIPTION
        "Cisco Firepower equipment:MemoryUnitDiscoveryModifierDef:policyLe
        vel managed object property"
    ::= { cfprEquipmentMemoryUnitDiscoveryModifierDefEntry 9 }

cfprEquipmentMemoryUnitDiscoveryModifierDefPolicyOwner OBJECT-TYPE
    SYNTAX       CfprPolicyPolicyOwner
    MAX-ACCESS   read-only
    STATUS       current
    DESCRIPTION
        "Cisco Firepower equipment:MemoryUnitDiscoveryModifierDef:policyOw
        ner managed object property"
    ::= { cfprEquipmentMemoryUnitDiscoveryModifierDefEntry 10 }

cfprEquipmentMgmtCapProviderTable OBJECT-TYPE
    SYNTAX           SEQUENCE OF CfprEquipmentMgmtCapProviderEntry
    MAX-ACCESS       not-accessible
    STATUS           current
    DESCRIPTION
        "Cisco Firepower equipment:MgmtCapProvider managed object table"
    ::= { cfprEquipmentObjects 89 }

cfprEquipmentMgmtCapProviderEntry OBJECT-TYPE
    SYNTAX           CfprEquipmentMgmtCapProviderEntry
    MAX-ACCESS       not-accessible
    STATUS           current
    DESCRIPTION
        "Entry for the cfprEquipmentMgmtCapProviderTable table."
    INDEX { cfprEquipmentMgmtCapProviderInstanceId }
    ::= { cfprEquipmentMgmtCapProviderTable 1 }

CfprEquipmentMgmtCapProviderEntry ::= SEQUENCE {
    cfprEquipmentMgmtCapProviderInstanceId                           CfprManagedObjectId,
    cfprEquipmentMgmtCapProviderDn                                   CfprManagedObjectDn,
    cfprEquipmentMgmtCapProviderRn                                   SnmpAdminString,
    cfprEquipmentMgmtCapProviderDeleted                              TruthValue,
    cfprEquipmentMgmtCapProviderDeprecated                           TruthValue,
    cfprEquipmentMgmtCapProviderElementLoadFailures                  Gauge32,
    cfprEquipmentMgmtCapProviderElementsLoaded                       Gauge32,
    cfprEquipmentMgmtCapProviderGencount                             Gauge32,
    cfprEquipmentMgmtCapProviderLoadErrors                           Gauge32,
    cfprEquipmentMgmtCapProviderLoadWarnings                         Gauge32,
    cfprEquipmentMgmtCapProviderMgmtPlaneVer                         SnmpAdminString,
    cfprEquipmentMgmtCapProviderModel                                SnmpAdminString,
    cfprEquipmentMgmtCapProviderPromCardType                         Gauge32,
    cfprEquipmentMgmtCapProviderRevision                             SnmpAdminString,
    cfprEquipmentMgmtCapProviderVendor                               SnmpAdminString
}

cfprEquipmentMgmtCapProviderInstanceId OBJECT-TYPE
    SYNTAX       CfprManagedObjectId
    MAX-ACCESS   not-accessible
    STATUS       current
    DESCRIPTION
        "Instance identifier of the managed object."
    ::= { cfprEquipmentMgmtCapProviderEntry 1 }

cfprEquipmentMgmtCapProviderDn OBJECT-TYPE
    SYNTAX       CfprManagedObjectDn
    MAX-ACCESS   read-only
    STATUS       current
    DESCRIPTION
        "Cisco Firepower equipment:MgmtCapProvider:dn managed
        object property"
    ::= { cfprEquipmentMgmtCapProviderEntry 2 }

cfprEquipmentMgmtCapProviderRn OBJECT-TYPE
    SYNTAX       SnmpAdminString
    MAX-ACCESS   read-only
    STATUS       current
    DESCRIPTION
        "Cisco Firepower equipment:MgmtCapProvider:rn managed
        object property"
    ::= { cfprEquipmentMgmtCapProviderEntry 3 }

cfprEquipmentMgmtCapProviderDeleted OBJECT-TYPE
    SYNTAX       TruthValue
    MAX-ACCESS   read-only
    STATUS       current
    DESCRIPTION
        "Cisco Firepower equipment:MgmtCapProvider:deleted
        managed object property"
    ::= { cfprEquipmentMgmtCapProviderEntry 4 }

cfprEquipmentMgmtCapProviderDeprecated OBJECT-TYPE
    SYNTAX       TruthValue
    MAX-ACCESS   read-only
    STATUS       current
    DESCRIPTION
        "Cisco Firepower equipment:MgmtCapProvider:deprecated
        managed object property"
    ::= { cfprEquipmentMgmtCapProviderEntry 5 }

cfprEquipmentMgmtCapProviderElementLoadFailures OBJECT-TYPE
    SYNTAX       Gauge32
    MAX-ACCESS   read-only
    STATUS       current
    DESCRIPTION
        "Cisco Firepower equipment:MgmtCapProvider:elementLoadFailures
        managed object property"
    ::= { cfprEquipmentMgmtCapProviderEntry 6 }

cfprEquipmentMgmtCapProviderElementsLoaded OBJECT-TYPE
    SYNTAX       Gauge32
    MAX-ACCESS   read-only
    STATUS       current
    DESCRIPTION
        "Cisco Firepower equipment:MgmtCapProvider:elementsLoaded
        managed object property"
    ::= { cfprEquipmentMgmtCapProviderEntry 7 }

cfprEquipmentMgmtCapProviderGencount OBJECT-TYPE
    SYNTAX       Gauge32
    MAX-ACCESS   read-only
    STATUS       current
    DESCRIPTION
        "Cisco Firepower equipment:MgmtCapProvider:gencount
        managed object property"
    ::= { cfprEquipmentMgmtCapProviderEntry 8 }

cfprEquipmentMgmtCapProviderLoadErrors OBJECT-TYPE
    SYNTAX       Gauge32
    MAX-ACCESS   read-only
    STATUS       current
    DESCRIPTION
        "Cisco Firepower equipment:MgmtCapProvider:loadErrors
        managed object property"
    ::= { cfprEquipmentMgmtCapProviderEntry 9 }

cfprEquipmentMgmtCapProviderLoadWarnings OBJECT-TYPE
    SYNTAX       Gauge32
    MAX-ACCESS   read-only
    STATUS       current
    DESCRIPTION
        "Cisco Firepower equipment:MgmtCapProvider:loadWarnings
        managed object property"
    ::= { cfprEquipmentMgmtCapProviderEntry 10 }

cfprEquipmentMgmtCapProviderMgmtPlaneVer OBJECT-TYPE
    SYNTAX       SnmpAdminString
    MAX-ACCESS   read-only
    STATUS       current
    DESCRIPTION
        "Cisco Firepower equipment:MgmtCapProvider:mgmtPlaneVer
        managed object property"
    ::= { cfprEquipmentMgmtCapProviderEntry 11 }

cfprEquipmentMgmtCapProviderModel OBJECT-TYPE
    SYNTAX       SnmpAdminString
    MAX-ACCESS   read-only
    STATUS       current
    DESCRIPTION
        "Cisco Firepower equipment:MgmtCapProvider:model
        managed object property"
    ::= { cfprEquipmentMgmtCapProviderEntry 12 }

cfprEquipmentMgmtCapProviderPromCardType OBJECT-TYPE
    SYNTAX       Gauge32
    MAX-ACCESS   read-only
    STATUS       current
    DESCRIPTION
        "Cisco Firepower equipment:MgmtCapProvider:promCardType
        managed object property"
    ::= { cfprEquipmentMgmtCapProviderEntry 13 }

cfprEquipmentMgmtCapProviderRevision OBJECT-TYPE
    SYNTAX       SnmpAdminString
    MAX-ACCESS   read-only
    STATUS       current
    DESCRIPTION
        "Cisco Firepower equipment:MgmtCapProvider:revision
        managed object property"
    ::= { cfprEquipmentMgmtCapProviderEntry 14 }

cfprEquipmentMgmtCapProviderVendor OBJECT-TYPE
    SYNTAX       SnmpAdminString
    MAX-ACCESS   read-only
    STATUS       current
    DESCRIPTION
        "Cisco Firepower equipment:MgmtCapProvider:vendor
        managed object property"
    ::= { cfprEquipmentMgmtCapProviderEntry 15 }

cfprEquipmentMgmtExtCapProviderTable OBJECT-TYPE
    SYNTAX           SEQUENCE OF CfprEquipmentMgmtExtCapProviderEntry
    MAX-ACCESS       not-accessible
    STATUS           current
    DESCRIPTION
        "Cisco Firepower equipment:MgmtExtCapProvider managed
        object table"
    ::= { cfprEquipmentObjects 90 }

cfprEquipmentMgmtExtCapProviderEntry OBJECT-TYPE
    SYNTAX           CfprEquipmentMgmtExtCapProviderEntry
    MAX-ACCESS       not-accessible
    STATUS           current
    DESCRIPTION
        "Entry for the cfprEquipmentMgmtExtCapProviderTable table."
    INDEX { cfprEquipmentMgmtExtCapProviderInstanceId }
    ::= { cfprEquipmentMgmtExtCapProviderTable 1 }

CfprEquipmentMgmtExtCapProviderEntry ::= SEQUENCE {
    cfprEquipmentMgmtExtCapProviderInstanceId                        CfprManagedObjectId,
    cfprEquipmentMgmtExtCapProviderDn                                CfprManagedObjectDn,
    cfprEquipmentMgmtExtCapProviderRn                                SnmpAdminString,
    cfprEquipmentMgmtExtCapProviderDeleted                           TruthValue,
    cfprEquipmentMgmtExtCapProviderDeprecated                        TruthValue,
    cfprEquipmentMgmtExtCapProviderElementLoadFailures               Gauge32,
    cfprEquipmentMgmtExtCapProviderElementsLoaded                    Gauge32,
    cfprEquipmentMgmtExtCapProviderGencount                          Gauge32,
    cfprEquipmentMgmtExtCapProviderLoadErrors                        Gauge32,
    cfprEquipmentMgmtExtCapProviderLoadWarnings                      Gauge32,
    cfprEquipmentMgmtExtCapProviderMgmtPlaneVer                      SnmpAdminString,
    cfprEquipmentMgmtExtCapProviderModel                             SnmpAdminString,
    cfprEquipmentMgmtExtCapProviderPromCardType                      Gauge32,
    cfprEquipmentMgmtExtCapProviderRevision                          SnmpAdminString,
    cfprEquipmentMgmtExtCapProviderVendor                            SnmpAdminString
}

cfprEquipmentMgmtExtCapProviderInstanceId OBJECT-TYPE
    SYNTAX       CfprManagedObjectId
    MAX-ACCESS   not-accessible
    STATUS       current
    DESCRIPTION
        "Instance identifier of the managed object."
    ::= { cfprEquipmentMgmtExtCapProviderEntry 1 }

cfprEquipmentMgmtExtCapProviderDn OBJECT-TYPE
    SYNTAX       CfprManagedObjectDn
    MAX-ACCESS   read-only
    STATUS       current
    DESCRIPTION
        "Cisco Firepower equipment:MgmtExtCapProvider:dn
        managed object property"
    ::= { cfprEquipmentMgmtExtCapProviderEntry 2 }

cfprEquipmentMgmtExtCapProviderRn OBJECT-TYPE
    SYNTAX       SnmpAdminString
    MAX-ACCESS   read-only
    STATUS       current
    DESCRIPTION
        "Cisco Firepower equipment:MgmtExtCapProvider:rn
        managed object property"
    ::= { cfprEquipmentMgmtExtCapProviderEntry 3 }

cfprEquipmentMgmtExtCapProviderDeleted OBJECT-TYPE
    SYNTAX       TruthValue
    MAX-ACCESS   read-only
    STATUS       current
    DESCRIPTION
        "Cisco Firepower equipment:MgmtExtCapProvider:deleted
        managed object property"
    ::= { cfprEquipmentMgmtExtCapProviderEntry 4 }

cfprEquipmentMgmtExtCapProviderDeprecated OBJECT-TYPE
    SYNTAX       TruthValue
    MAX-ACCESS   read-only
    STATUS       current
    DESCRIPTION
        "Cisco Firepower equipment:MgmtExtCapProvider:deprecated
        managed object property"
    ::= { cfprEquipmentMgmtExtCapProviderEntry 5 }

cfprEquipmentMgmtExtCapProviderElementLoadFailures OBJECT-TYPE
    SYNTAX       Gauge32
    MAX-ACCESS   read-only
    STATUS       current
    DESCRIPTION
        "Cisco Firepower equipment:MgmtExtCapProvider:elementLoadFailures
        managed object property"
    ::= { cfprEquipmentMgmtExtCapProviderEntry 6 }

cfprEquipmentMgmtExtCapProviderElementsLoaded OBJECT-TYPE
    SYNTAX       Gauge32
    MAX-ACCESS   read-only
    STATUS       current
    DESCRIPTION
        "Cisco Firepower equipment:MgmtExtCapProvider:elementsLoaded
        managed object property"
    ::= { cfprEquipmentMgmtExtCapProviderEntry 7 }

cfprEquipmentMgmtExtCapProviderGencount OBJECT-TYPE
    SYNTAX       Gauge32
    MAX-ACCESS   read-only
    STATUS       current
    DESCRIPTION
        "Cisco Firepower equipment:MgmtExtCapProvider:gencount
        managed object property"
    ::= { cfprEquipmentMgmtExtCapProviderEntry 8 }

cfprEquipmentMgmtExtCapProviderLoadErrors OBJECT-TYPE
    SYNTAX       Gauge32
    MAX-ACCESS   read-only
    STATUS       current
    DESCRIPTION
        "Cisco Firepower equipment:MgmtExtCapProvider:loadErrors
        managed object property"
    ::= { cfprEquipmentMgmtExtCapProviderEntry 9 }

cfprEquipmentMgmtExtCapProviderLoadWarnings OBJECT-TYPE
    SYNTAX       Gauge32
    MAX-ACCESS   read-only
    STATUS       current
    DESCRIPTION
        "Cisco Firepower equipment:MgmtExtCapProvider:loadWarnings
        managed object property"
    ::= { cfprEquipmentMgmtExtCapProviderEntry 10 }

cfprEquipmentMgmtExtCapProviderMgmtPlaneVer OBJECT-TYPE
    SYNTAX       SnmpAdminString
    MAX-ACCESS   read-only
    STATUS       current
    DESCRIPTION
        "Cisco Firepower equipment:MgmtExtCapProvider:mgmtPlaneVer
        managed object property"
    ::= { cfprEquipmentMgmtExtCapProviderEntry 11 }

cfprEquipmentMgmtExtCapProviderModel OBJECT-TYPE
    SYNTAX       SnmpAdminString
    MAX-ACCESS   read-only
    STATUS       current
    DESCRIPTION
        "Cisco Firepower equipment:MgmtExtCapProvider:model
        managed object property"
    ::= { cfprEquipmentMgmtExtCapProviderEntry 12 }

cfprEquipmentMgmtExtCapProviderPromCardType OBJECT-TYPE
    SYNTAX       Gauge32
    MAX-ACCESS   read-only
    STATUS       current
    DESCRIPTION
        "Cisco Firepower equipment:MgmtExtCapProvider:promCardType
        managed object property"
    ::= { cfprEquipmentMgmtExtCapProviderEntry 13 }

cfprEquipmentMgmtExtCapProviderRevision OBJECT-TYPE
    SYNTAX       SnmpAdminString
    MAX-ACCESS   read-only
    STATUS       current
    DESCRIPTION
        "Cisco Firepower equipment:MgmtExtCapProvider:revision
        managed object property"
    ::= { cfprEquipmentMgmtExtCapProviderEntry 14 }

cfprEquipmentMgmtExtCapProviderVendor OBJECT-TYPE
    SYNTAX       SnmpAdminString
    MAX-ACCESS   read-only
    STATUS       current
    DESCRIPTION
        "Cisco Firepower equipment:MgmtExtCapProvider:vendor
        managed object property"
    ::= { cfprEquipmentMgmtExtCapProviderEntry 15 }

cfprEquipmentNetworkElementFanStatsTable OBJECT-TYPE
    SYNTAX           SEQUENCE OF CfprEquipmentNetworkElementFanStatsEntry
    MAX-ACCESS       not-accessible
    STATUS           current
    DESCRIPTION
        "Cisco Firepower equipment:NetworkElementFanStats
        managed object table"
    ::= { cfprEquipmentObjects 91 }

cfprEquipmentNetworkElementFanStatsEntry OBJECT-TYPE
    SYNTAX           CfprEquipmentNetworkElementFanStatsEntry
    MAX-ACCESS       not-accessible
    STATUS           current
    DESCRIPTION
        "Entry for the cfprEquipmentNetworkElementFanStatsTable table."
    INDEX { cfprEquipmentNetworkElementFanStatsInstanceId }
    ::= { cfprEquipmentNetworkElementFanStatsTable 1 }

CfprEquipmentNetworkElementFanStatsEntry ::= SEQUENCE {
    cfprEquipmentNetworkElementFanStatsInstanceId                    CfprManagedObjectId,
    cfprEquipmentNetworkElementFanStatsDn                            CfprManagedObjectDn,
    cfprEquipmentNetworkElementFanStatsRn                            SnmpAdminString,
    cfprEquipmentNetworkElementFanStatsAirflowDirection              CfprEquipmentAirflowDirection,
    cfprEquipmentNetworkElementFanStatsDrivePercentage               Gauge32,
    cfprEquipmentNetworkElementFanStatsDrivePercentageAvg            Gauge32,
    cfprEquipmentNetworkElementFanStatsDrivePercentageMax            Gauge32,
    cfprEquipmentNetworkElementFanStatsDrivePercentageMin            Gauge32,
    cfprEquipmentNetworkElementFanStatsIntervals                     Gauge32,
    cfprEquipmentNetworkElementFanStatsSpeed                         Gauge32,
    cfprEquipmentNetworkElementFanStatsSpeedAvg                      Gauge32,
    cfprEquipmentNetworkElementFanStatsSpeedMax                      Gauge32,
    cfprEquipmentNetworkElementFanStatsSpeedMin                      Gauge32,
    cfprEquipmentNetworkElementFanStatsSuspect                       TruthValue,
    cfprEquipmentNetworkElementFanStatsThresholded                   CfprEquipmentNetworkElementFanStatsThresholded,
    cfprEquipmentNetworkElementFanStatsTimeCollected                 DateAndTime,
    cfprEquipmentNetworkElementFanStatsUpdate                        Gauge32
}

cfprEquipmentNetworkElementFanStatsInstanceId OBJECT-TYPE
    SYNTAX       CfprManagedObjectId
    MAX-ACCESS   not-accessible
    STATUS       current
    DESCRIPTION
        "Instance identifier of the managed object."
    ::= { cfprEquipmentNetworkElementFanStatsEntry 1 }

cfprEquipmentNetworkElementFanStatsDn OBJECT-TYPE
    SYNTAX       CfprManagedObjectDn
    MAX-ACCESS   read-only
    STATUS       current
    DESCRIPTION
        "Cisco Firepower equipment:NetworkElementFanStats:dn
        managed object property"
    ::= { cfprEquipmentNetworkElementFanStatsEntry 2 }

cfprEquipmentNetworkElementFanStatsRn OBJECT-TYPE
    SYNTAX       SnmpAdminString
    MAX-ACCESS   read-only
    STATUS       current
    DESCRIPTION
        "Cisco Firepower equipment:NetworkElementFanStats:rn
        managed object property"
    ::= { cfprEquipmentNetworkElementFanStatsEntry 3 }

cfprEquipmentNetworkElementFanStatsAirflowDirection OBJECT-TYPE
    SYNTAX       CfprEquipmentAirflowDirection
    MAX-ACCESS   read-only
    STATUS       current
    DESCRIPTION
        "Cisco Firepower equipment:NetworkElementFanStats:airflowDirection
         managed object property"
    ::= { cfprEquipmentNetworkElementFanStatsEntry 4 }

cfprEquipmentNetworkElementFanStatsDrivePercentage OBJECT-TYPE
    SYNTAX       Gauge32
    MAX-ACCESS   read-only
    STATUS       current
    DESCRIPTION
        "Cisco Firepower equipment:NetworkElementFanStats:drivePercentage
        managed object property"
    ::= { cfprEquipmentNetworkElementFanStatsEntry 5 }

cfprEquipmentNetworkElementFanStatsDrivePercentageAvg OBJECT-TYPE
    SYNTAX       Gauge32
    MAX-ACCESS   read-only
    STATUS       current
    DESCRIPTION
        "Cisco Firepower equipment:NetworkElementFanStats:drivePercentageA
        vg managed object property"
    ::= { cfprEquipmentNetworkElementFanStatsEntry 6 }

cfprEquipmentNetworkElementFanStatsDrivePercentageMax OBJECT-TYPE
    SYNTAX       Gauge32
    MAX-ACCESS   read-only
    STATUS       current
    DESCRIPTION
        "Cisco Firepower equipment:NetworkElementFanStats:drivePercentageM
        ax managed object property"
    ::= { cfprEquipmentNetworkElementFanStatsEntry 7 }

cfprEquipmentNetworkElementFanStatsDrivePercentageMin OBJECT-TYPE
    SYNTAX       Gauge32
    MAX-ACCESS   read-only
    STATUS       current
    DESCRIPTION
        "Cisco Firepower equipment:NetworkElementFanStats:drivePercentageM
        in managed object property"
    ::= { cfprEquipmentNetworkElementFanStatsEntry 8 }

cfprEquipmentNetworkElementFanStatsIntervals OBJECT-TYPE
    SYNTAX       Gauge32
    MAX-ACCESS   read-only
    STATUS       current
    DESCRIPTION
        "Cisco Firepower equipment:NetworkElementFanStats:intervals
        managed object property"
    ::= { cfprEquipmentNetworkElementFanStatsEntry 9 }

cfprEquipmentNetworkElementFanStatsSpeed OBJECT-TYPE
    SYNTAX       Gauge32
    MAX-ACCESS   read-only
    STATUS       current
    DESCRIPTION
        "Cisco Firepower equipment:NetworkElementFanStats:speed
        managed object property"
    ::= { cfprEquipmentNetworkElementFanStatsEntry 10 }

cfprEquipmentNetworkElementFanStatsSpeedAvg OBJECT-TYPE
    SYNTAX       Gauge32
    MAX-ACCESS   read-only
    STATUS       current
    DESCRIPTION
        "Cisco Firepower equipment:NetworkElementFanStats:speedAvg
        managed object property"
    ::= { cfprEquipmentNetworkElementFanStatsEntry 11 }

cfprEquipmentNetworkElementFanStatsSpeedMax OBJECT-TYPE
    SYNTAX       Gauge32
    MAX-ACCESS   read-only
    STATUS       current
    DESCRIPTION
        "Cisco Firepower equipment:NetworkElementFanStats:speedMax
        managed object property"
    ::= { cfprEquipmentNetworkElementFanStatsEntry 12 }

cfprEquipmentNetworkElementFanStatsSpeedMin OBJECT-TYPE
    SYNTAX       Gauge32
    MAX-ACCESS   read-only
    STATUS       current
    DESCRIPTION
        "Cisco Firepower equipment:NetworkElementFanStats:speedMin
        managed object property"
    ::= { cfprEquipmentNetworkElementFanStatsEntry 13 }

cfprEquipmentNetworkElementFanStatsSuspect OBJECT-TYPE
    SYNTAX       TruthValue
    MAX-ACCESS   read-only
    STATUS       current
    DESCRIPTION
        "Cisco Firepower equipment:NetworkElementFanStats:suspect
        managed object property"
    ::= { cfprEquipmentNetworkElementFanStatsEntry 14 }

cfprEquipmentNetworkElementFanStatsThresholded OBJECT-TYPE
    SYNTAX       CfprEquipmentNetworkElementFanStatsThresholded
    MAX-ACCESS   read-only
    STATUS       current
    DESCRIPTION
        "Cisco Firepower equipment:NetworkElementFanStats:thresholded
        managed object property"
    ::= { cfprEquipmentNetworkElementFanStatsEntry 15 }

cfprEquipmentNetworkElementFanStatsTimeCollected OBJECT-TYPE
    SYNTAX       DateAndTime
    MAX-ACCESS   read-only
    STATUS       current
    DESCRIPTION
        "Cisco Firepower equipment:NetworkElementFanStats:timeCollected
        managed object property"
    ::= { cfprEquipmentNetworkElementFanStatsEntry 16 }

cfprEquipmentNetworkElementFanStatsUpdate OBJECT-TYPE
    SYNTAX       Gauge32
    MAX-ACCESS   read-only
    STATUS       current
    DESCRIPTION
        "Cisco Firepower equipment:NetworkElementFanStats:update
        managed object property"
    ::= { cfprEquipmentNetworkElementFanStatsEntry 17 }

cfprEquipmentNetworkElementFanStatsHistTable OBJECT-TYPE
    SYNTAX           SEQUENCE OF CfprEquipmentNetworkElementFanStatsHistEntry
    MAX-ACCESS       not-accessible
    STATUS           current
    DESCRIPTION
        "Cisco Firepower equipment:NetworkElementFanStatsHist
        managed object table"
    ::= { cfprEquipmentObjects 92 }

cfprEquipmentNetworkElementFanStatsHistEntry OBJECT-TYPE
    SYNTAX           CfprEquipmentNetworkElementFanStatsHistEntry
    MAX-ACCESS       not-accessible
    STATUS           current
    DESCRIPTION
        "Entry for the cfprEquipmentNetworkElementFanStatsHistTable table."
    INDEX { cfprEquipmentNetworkElementFanStatsHistInstanceId }
    ::= { cfprEquipmentNetworkElementFanStatsHistTable 1 }

CfprEquipmentNetworkElementFanStatsHistEntry ::= SEQUENCE {
    cfprEquipmentNetworkElementFanStatsHistInstanceId                CfprManagedObjectId,
    cfprEquipmentNetworkElementFanStatsHistDn                        CfprManagedObjectDn,
    cfprEquipmentNetworkElementFanStatsHistRn                        SnmpAdminString,
    cfprEquipmentNetworkElementFanStatsHistDrivePercentage           Gauge32,
    cfprEquipmentNetworkElementFanStatsHistDrivePercentageAvg        Gauge32,
    cfprEquipmentNetworkElementFanStatsHistDrivePercentageMax        Gauge32,
    cfprEquipmentNetworkElementFanStatsHistDrivePercentageMin        Gauge32,
    cfprEquipmentNetworkElementFanStatsHistId                        Unsigned64,
    cfprEquipmentNetworkElementFanStatsHistMostRecent                TruthValue,
    cfprEquipmentNetworkElementFanStatsHistSpeed                     Gauge32,
    cfprEquipmentNetworkElementFanStatsHistSpeedAvg                  Gauge32,
    cfprEquipmentNetworkElementFanStatsHistSpeedMax                  Gauge32,
    cfprEquipmentNetworkElementFanStatsHistSpeedMin                  Gauge32,
    cfprEquipmentNetworkElementFanStatsHistSuspect                   TruthValue,
    cfprEquipmentNetworkElementFanStatsHistThresholded               CfprEquipmentNetworkElementFanStatsHistThresholded,
    cfprEquipmentNetworkElementFanStatsHistTimeCollected             DateAndTime
}

cfprEquipmentNetworkElementFanStatsHistInstanceId OBJECT-TYPE
    SYNTAX       CfprManagedObjectId
    MAX-ACCESS   not-accessible
    STATUS       current
    DESCRIPTION
        "Instance identifier of the managed object."
    ::= { cfprEquipmentNetworkElementFanStatsHistEntry 1 }

cfprEquipmentNetworkElementFanStatsHistDn OBJECT-TYPE
    SYNTAX       CfprManagedObjectDn
    MAX-ACCESS   read-only
    STATUS       current
    DESCRIPTION
        "Cisco Firepower equipment:NetworkElementFanStatsHist:dn
        managed object property"
    ::= { cfprEquipmentNetworkElementFanStatsHistEntry 2 }

cfprEquipmentNetworkElementFanStatsHistRn OBJECT-TYPE
    SYNTAX       SnmpAdminString
    MAX-ACCESS   read-only
    STATUS       current
    DESCRIPTION
        "Cisco Firepower equipment:NetworkElementFanStatsHist:rn
        managed object property"
    ::= { cfprEquipmentNetworkElementFanStatsHistEntry 3 }

cfprEquipmentNetworkElementFanStatsHistDrivePercentage OBJECT-TYPE
    SYNTAX       Gauge32
    MAX-ACCESS   read-only
    STATUS       current
    DESCRIPTION
        "Cisco Firepower equipment:NetworkElementFanStatsHist:drivePercent
        age managed object property"
    ::= { cfprEquipmentNetworkElementFanStatsHistEntry 4 }

cfprEquipmentNetworkElementFanStatsHistDrivePercentageAvg OBJECT-TYPE
    SYNTAX       Gauge32
    MAX-ACCESS   read-only
    STATUS       current
    DESCRIPTION
        "Cisco Firepower equipment:NetworkElementFanStatsHist:drivePercent
        ageAvg managed object property"
    ::= { cfprEquipmentNetworkElementFanStatsHistEntry 5 }

cfprEquipmentNetworkElementFanStatsHistDrivePercentageMax OBJECT-TYPE
    SYNTAX       Gauge32
    MAX-ACCESS   read-only
    STATUS       current
    DESCRIPTION
        "Cisco Firepower equipment:NetworkElementFanStatsHist:drivePercent
        ageMax managed object property"
    ::= { cfprEquipmentNetworkElementFanStatsHistEntry 6 }

cfprEquipmentNetworkElementFanStatsHistDrivePercentageMin OBJECT-TYPE
    SYNTAX       Gauge32
    MAX-ACCESS   read-only
    STATUS       current
    DESCRIPTION
        "Cisco Firepower equipment:NetworkElementFanStatsHist:drivePercent
        ageMin managed object property"
    ::= { cfprEquipmentNetworkElementFanStatsHistEntry 7 }

cfprEquipmentNetworkElementFanStatsHistId OBJECT-TYPE
    SYNTAX       Unsigned64
    MAX-ACCESS   read-only
    STATUS       current
    DESCRIPTION
        "Cisco Firepower equipment:NetworkElementFanStatsHist:id
        managed object property"
    ::= { cfprEquipmentNetworkElementFanStatsHistEntry 8 }

cfprEquipmentNetworkElementFanStatsHistMostRecent OBJECT-TYPE
    SYNTAX       TruthValue
    MAX-ACCESS   read-only
    STATUS       current
    DESCRIPTION
        "Cisco Firepower equipment:NetworkElementFanStatsHist:mostRecent
        managed object property"
    ::= { cfprEquipmentNetworkElementFanStatsHistEntry 9 }

cfprEquipmentNetworkElementFanStatsHistSpeed OBJECT-TYPE
    SYNTAX       Gauge32
    MAX-ACCESS   read-only
    STATUS       current
    DESCRIPTION
        "Cisco Firepower equipment:NetworkElementFanStatsHist:speed
        managed object property"
    ::= { cfprEquipmentNetworkElementFanStatsHistEntry 10 }

cfprEquipmentNetworkElementFanStatsHistSpeedAvg OBJECT-TYPE
    SYNTAX       Gauge32
    MAX-ACCESS   read-only
    STATUS       current
    DESCRIPTION
        "Cisco Firepower equipment:NetworkElementFanStatsHist:speedAvg
        managed object property"
    ::= { cfprEquipmentNetworkElementFanStatsHistEntry 11 }

cfprEquipmentNetworkElementFanStatsHistSpeedMax OBJECT-TYPE
    SYNTAX       Gauge32
    MAX-ACCESS   read-only
    STATUS       current
    DESCRIPTION
        "Cisco Firepower equipment:NetworkElementFanStatsHist:speedMax
        managed object property"
    ::= { cfprEquipmentNetworkElementFanStatsHistEntry 12 }

cfprEquipmentNetworkElementFanStatsHistSpeedMin OBJECT-TYPE
    SYNTAX       Gauge32
    MAX-ACCESS   read-only
    STATUS       current
    DESCRIPTION
        "Cisco Firepower equipment:NetworkElementFanStatsHist:speedMin
        managed object property"
    ::= { cfprEquipmentNetworkElementFanStatsHistEntry 13 }

cfprEquipmentNetworkElementFanStatsHistSuspect OBJECT-TYPE
    SYNTAX       TruthValue
    MAX-ACCESS   read-only
    STATUS       current
    DESCRIPTION
        "Cisco Firepower equipment:NetworkElementFanStatsHist:suspect
        managed object property"
    ::= { cfprEquipmentNetworkElementFanStatsHistEntry 14 }

cfprEquipmentNetworkElementFanStatsHistThresholded OBJECT-TYPE
    SYNTAX       CfprEquipmentNetworkElementFanStatsHistThresholded
    MAX-ACCESS   read-only
    STATUS       current
    DESCRIPTION
        "Cisco Firepower equipment:NetworkElementFanStatsHist:thresholded
        managed object property"
    ::= { cfprEquipmentNetworkElementFanStatsHistEntry 15 }

cfprEquipmentNetworkElementFanStatsHistTimeCollected OBJECT-TYPE
    SYNTAX       DateAndTime
    MAX-ACCESS   read-only
    STATUS       current
    DESCRIPTION
        "Cisco Firepower equipment:NetworkElementFanStatsHist:timeCollecte
        d managed object property"
    ::= { cfprEquipmentNetworkElementFanStatsHistEntry 16 }

cfprEquipmentOsBootParamTable OBJECT-TYPE
    SYNTAX           SEQUENCE OF CfprEquipmentOsBootParamEntry
    MAX-ACCESS       not-accessible
    STATUS           current
    DESCRIPTION
        "Cisco Firepower equipment:OsBootParam managed object table"
    ::= { cfprEquipmentObjects 156 }

cfprEquipmentOsBootParamEntry OBJECT-TYPE
    SYNTAX           CfprEquipmentOsBootParamEntry
    MAX-ACCESS       not-accessible
    STATUS           current
    DESCRIPTION
        "Entry for the cfprEquipmentOsBootParamTable table."
    INDEX { cfprEquipmentOsBootParamInstanceId }
    ::= { cfprEquipmentOsBootParamTable 1 }

CfprEquipmentOsBootParamEntry ::= SEQUENCE {
    cfprEquipmentOsBootParamInstanceId                               CfprManagedObjectId,
    cfprEquipmentOsBootParamDn                                       CfprManagedObjectDn,
    cfprEquipmentOsBootParamRn                                       SnmpAdminString,
    cfprEquipmentOsBootParamAppType                                  CfprEquipmentAppType,
    cfprEquipmentOsBootParamDmaSize                                  SnmpAdminString,
    cfprEquipmentOsBootParamHeapSize                                 SnmpAdminString,
    cfprEquipmentOsBootParamNumPage                                  SnmpAdminString,
    cfprEquipmentOsBootParamPageSize                                 SnmpAdminString,
    cfprEquipmentOsBootParamPti                                      SnmpAdminString
}

cfprEquipmentOsBootParamInstanceId OBJECT-TYPE
    SYNTAX       CfprManagedObjectId
    MAX-ACCESS   not-accessible
    STATUS       current
    DESCRIPTION
        "Instance identifier of the managed object."
    ::= { cfprEquipmentOsBootParamEntry 1 }

cfprEquipmentOsBootParamDn OBJECT-TYPE
    SYNTAX       CfprManagedObjectDn
    MAX-ACCESS   read-only
    STATUS       current
    DESCRIPTION
        "Cisco Firepower equipment:OsBootParam:dn managed object property"
    ::= { cfprEquipmentOsBootParamEntry 2 }

cfprEquipmentOsBootParamRn OBJECT-TYPE
    SYNTAX       SnmpAdminString
    MAX-ACCESS   read-only
    STATUS       current
    DESCRIPTION
        "Cisco Firepower equipment:OsBootParam:rn managed object property"
    ::= { cfprEquipmentOsBootParamEntry 3 }

cfprEquipmentOsBootParamAppType OBJECT-TYPE
    SYNTAX       CfprEquipmentAppType
    MAX-ACCESS   read-only
    STATUS       current
    DESCRIPTION
        "Cisco Firepower equipment:OsBootParam:appType
        managed object property"
    ::= { cfprEquipmentOsBootParamEntry 4 }

cfprEquipmentOsBootParamDmaSize OBJECT-TYPE
    SYNTAX       SnmpAdminString
    MAX-ACCESS   read-only
    STATUS       current
    DESCRIPTION
        "Cisco Firepower equipment:OsBootParam:dmaSize
        managed object property"
    ::= { cfprEquipmentOsBootParamEntry 5 }

cfprEquipmentOsBootParamHeapSize OBJECT-TYPE
    SYNTAX       SnmpAdminString
    MAX-ACCESS   read-only
    STATUS       current
    DESCRIPTION
        "Cisco Firepower equipment:OsBootParam:heapSize
        managed object property"
    ::= { cfprEquipmentOsBootParamEntry 6 }

cfprEquipmentOsBootParamNumPage OBJECT-TYPE
    SYNTAX       SnmpAdminString
    MAX-ACCESS   read-only
    STATUS       current
    DESCRIPTION
        "Cisco Firepower equipment:OsBootParam:numPage
        managed object property"
    ::= { cfprEquipmentOsBootParamEntry 7 }

cfprEquipmentOsBootParamPageSize OBJECT-TYPE
    SYNTAX       SnmpAdminString
    MAX-ACCESS   read-only
    STATUS       current
    DESCRIPTION
        "Cisco Firepower equipment:OsBootParam:pageSize
        managed object property"
    ::= { cfprEquipmentOsBootParamEntry 8 }

cfprEquipmentOsBootParamPti OBJECT-TYPE
    SYNTAX       SnmpAdminString
    MAX-ACCESS   read-only
    STATUS       current
    DESCRIPTION
        "Cisco Firepower equipment:OsBootParam:pti managed
        object property"
    ::= { cfprEquipmentOsBootParamEntry 9 }

cfprEquipmentPOSTTable OBJECT-TYPE
    SYNTAX           SEQUENCE OF CfprEquipmentPOSTEntry
    MAX-ACCESS       not-accessible
    STATUS           current
    DESCRIPTION
        "Cisco Firepower equipment:POST managed object table"
    ::= { cfprEquipmentObjects 93 }

cfprEquipmentPOSTEntry OBJECT-TYPE
    SYNTAX           CfprEquipmentPOSTEntry
    MAX-ACCESS       not-accessible
    STATUS           current
    DESCRIPTION
        "Entry for the cfprEquipmentPOSTTable table."
    INDEX { cfprEquipmentPOSTInstanceId }
    ::= { cfprEquipmentPOSTTable 1 }

CfprEquipmentPOSTEntry ::= SEQUENCE {
    cfprEquipmentPOSTInstanceId                                      CfprManagedObjectId,
    cfprEquipmentPOSTDn                                              CfprManagedObjectDn,
    cfprEquipmentPOSTRn                                              SnmpAdminString,
    cfprEquipmentPOSTCode                                            SnmpAdminString,
    cfprEquipmentPOSTCreated                                         DateAndTime,
    cfprEquipmentPOSTDescr                                           SnmpAdminString,
    cfprEquipmentPOSTGlobalId                                        SnmpAdminString,
    cfprEquipmentPOSTLocalId                                         SnmpAdminString,
    cfprEquipmentPOSTMethod                                          CfprEquipmentMethod,
    cfprEquipmentPOSTName                                            SnmpAdminString,
    cfprEquipmentPOSTRecoverable                                     CfprEquipmentPOSTRecoverability,
    cfprEquipmentPOSTRecoveryAction                                  SnmpAdminString,
    cfprEquipmentPOSTSeverity                                        CfprConditionSeverity,
    cfprEquipmentPOSTType                                            SnmpAdminString,
    cfprEquipmentPOSTValue                                           Gauge32
}

cfprEquipmentPOSTInstanceId OBJECT-TYPE
    SYNTAX       CfprManagedObjectId
    MAX-ACCESS   not-accessible
    STATUS       current
    DESCRIPTION
        "Instance identifier of the managed object."
    ::= { cfprEquipmentPOSTEntry 1 }

cfprEquipmentPOSTDn OBJECT-TYPE
    SYNTAX       CfprManagedObjectDn
    MAX-ACCESS   read-only
    STATUS       current
    DESCRIPTION
        "Cisco Firepower equipment:POST:dn managed object property"
    ::= { cfprEquipmentPOSTEntry 2 }

cfprEquipmentPOSTRn OBJECT-TYPE
    SYNTAX       SnmpAdminString
    MAX-ACCESS   read-only
    STATUS       current
    DESCRIPTION
        "Cisco Firepower equipment:POST:rn managed object property"
    ::= { cfprEquipmentPOSTEntry 3 }

cfprEquipmentPOSTCode OBJECT-TYPE
    SYNTAX       SnmpAdminString
    MAX-ACCESS   read-only
    STATUS       current
    DESCRIPTION
        "Cisco Firepower equipment:POST:code managed object property"
    ::= { cfprEquipmentPOSTEntry 4 }

cfprEquipmentPOSTCreated OBJECT-TYPE
    SYNTAX       DateAndTime
    MAX-ACCESS   read-only
    STATUS       current
    DESCRIPTION
        "Cisco Firepower equipment:POST:created managed object property"
    ::= { cfprEquipmentPOSTEntry 5 }

cfprEquipmentPOSTDescr OBJECT-TYPE
    SYNTAX       SnmpAdminString
    MAX-ACCESS   read-only
    STATUS       current
    DESCRIPTION
        "Cisco Firepower equipment:POST:descr managed object property"
    ::= { cfprEquipmentPOSTEntry 6 }

cfprEquipmentPOSTGlobalId OBJECT-TYPE
    SYNTAX       SnmpAdminString
    MAX-ACCESS   read-only
    STATUS       current
    DESCRIPTION
        "Cisco Firepower equipment:POST:globalId managed object property"
    ::= { cfprEquipmentPOSTEntry 7 }

cfprEquipmentPOSTLocalId OBJECT-TYPE
    SYNTAX       SnmpAdminString
    MAX-ACCESS   read-only
    STATUS       current
    DESCRIPTION
        "Cisco Firepower equipment:POST:localId managed object property"
    ::= { cfprEquipmentPOSTEntry 8 }

cfprEquipmentPOSTMethod OBJECT-TYPE
    SYNTAX       CfprEquipmentMethod
    MAX-ACCESS   read-only
    STATUS       current
    DESCRIPTION
        "Cisco Firepower equipment:POST:method managed object property"
    ::= { cfprEquipmentPOSTEntry 9 }

cfprEquipmentPOSTName OBJECT-TYPE
    SYNTAX       SnmpAdminString
    MAX-ACCESS   read-only
    STATUS       current
    DESCRIPTION
        "Cisco Firepower equipment:POST:name managed object property"
    ::= { cfprEquipmentPOSTEntry 10 }

cfprEquipmentPOSTRecoverable OBJECT-TYPE
    SYNTAX       CfprEquipmentPOSTRecoverability
    MAX-ACCESS   read-only
    STATUS       current
    DESCRIPTION
        "Cisco Firepower equipment:POST:recoverable managed
        object property"
    ::= { cfprEquipmentPOSTEntry 11 }

cfprEquipmentPOSTRecoveryAction OBJECT-TYPE
    SYNTAX       SnmpAdminString
    MAX-ACCESS   read-only
    STATUS       current
    DESCRIPTION
        "Cisco Firepower equipment:POST:recoveryAction
        managed object property"
    ::= { cfprEquipmentPOSTEntry 12 }

cfprEquipmentPOSTSeverity OBJECT-TYPE
    SYNTAX       CfprConditionSeverity
    MAX-ACCESS   read-only
    STATUS       current
    DESCRIPTION
        "Cisco Firepower equipment:POST:severity managed object property"
    ::= { cfprEquipmentPOSTEntry 13 }

cfprEquipmentPOSTType OBJECT-TYPE
    SYNTAX       SnmpAdminString
    MAX-ACCESS   read-only
    STATUS       current
    DESCRIPTION
        "Cisco Firepower equipment:POST:type managed object property"
    ::= { cfprEquipmentPOSTEntry 14 }

cfprEquipmentPOSTValue OBJECT-TYPE
    SYNTAX       Gauge32
    MAX-ACCESS   read-only
    STATUS       current
    DESCRIPTION
        "Cisco Firepower equipment:POST:value managed object property"
    ::= { cfprEquipmentPOSTEntry 15 }

cfprEquipmentPOSTCodeTable OBJECT-TYPE
    SYNTAX           SEQUENCE OF CfprEquipmentPOSTCodeEntry
    MAX-ACCESS       not-accessible
    STATUS           current
    DESCRIPTION
        "Cisco Firepower equipment:POSTCode managed object table"
    ::= { cfprEquipmentObjects 94 }

cfprEquipmentPOSTCodeEntry OBJECT-TYPE
    SYNTAX           CfprEquipmentPOSTCodeEntry
    MAX-ACCESS       not-accessible
    STATUS           current
    DESCRIPTION
        "Entry for the cfprEquipmentPOSTCodeTable table."
    INDEX { cfprEquipmentPOSTCodeInstanceId }
    ::= { cfprEquipmentPOSTCodeTable 1 }

CfprEquipmentPOSTCodeEntry ::= SEQUENCE {
    cfprEquipmentPOSTCodeInstanceId                                  CfprManagedObjectId,
    cfprEquipmentPOSTCodeDn                                          CfprManagedObjectDn,
    cfprEquipmentPOSTCodeRn                                          SnmpAdminString,
    cfprEquipmentPOSTCodeCode                                        SnmpAdminString,
    cfprEquipmentPOSTCodeDescr                                       SnmpAdminString,
    cfprEquipmentPOSTCodeGlobalId                                    SnmpAdminString,
    cfprEquipmentPOSTCodeLocalId                                     SnmpAdminString,
    cfprEquipmentPOSTCodeMethod                                      CfprEquipmentMethod,
    cfprEquipmentPOSTCodeName                                        SnmpAdminString,
    cfprEquipmentPOSTCodeRecoverable                                 CfprEquipmentPOSTRecoverability,
    cfprEquipmentPOSTCodeRecoveryAction                              SnmpAdminString,
    cfprEquipmentPOSTCodeSeverity                                    CfprConditionSeverity
}

cfprEquipmentPOSTCodeInstanceId OBJECT-TYPE
    SYNTAX       CfprManagedObjectId
    MAX-ACCESS   not-accessible
    STATUS       current
    DESCRIPTION
        "Instance identifier of the managed object."
    ::= { cfprEquipmentPOSTCodeEntry 1 }

cfprEquipmentPOSTCodeDn OBJECT-TYPE
    SYNTAX       CfprManagedObjectDn
    MAX-ACCESS   read-only
    STATUS       current
    DESCRIPTION
        "Cisco Firepower equipment:POSTCode:dn managed object property"
    ::= { cfprEquipmentPOSTCodeEntry 2 }

cfprEquipmentPOSTCodeRn OBJECT-TYPE
    SYNTAX       SnmpAdminString
    MAX-ACCESS   read-only
    STATUS       current
    DESCRIPTION
        "Cisco Firepower equipment:POSTCode:rn managed object property"
    ::= { cfprEquipmentPOSTCodeEntry 3 }

cfprEquipmentPOSTCodeCode OBJECT-TYPE
    SYNTAX       SnmpAdminString
    MAX-ACCESS   read-only
    STATUS       current
    DESCRIPTION
        "Cisco Firepower equipment:POSTCode:code managed object property"
    ::= { cfprEquipmentPOSTCodeEntry 4 }

cfprEquipmentPOSTCodeDescr OBJECT-TYPE
    SYNTAX       SnmpAdminString
    MAX-ACCESS   read-only
    STATUS       current
    DESCRIPTION
        "Cisco Firepower equipment:POSTCode:descr managed object property"
    ::= { cfprEquipmentPOSTCodeEntry 5 }

cfprEquipmentPOSTCodeGlobalId OBJECT-TYPE
    SYNTAX       SnmpAdminString
    MAX-ACCESS   read-only
    STATUS       current
    DESCRIPTION
        "Cisco Firepower equipment:POSTCode:globalId managed
        object property"
    ::= { cfprEquipmentPOSTCodeEntry 6 }

cfprEquipmentPOSTCodeLocalId OBJECT-TYPE
    SYNTAX       SnmpAdminString
    MAX-ACCESS   read-only
    STATUS       current
    DESCRIPTION
        "Cisco Firepower equipment:POSTCode:localId managed
        object property"
    ::= { cfprEquipmentPOSTCodeEntry 7 }

cfprEquipmentPOSTCodeMethod OBJECT-TYPE
    SYNTAX       CfprEquipmentMethod
    MAX-ACCESS   read-only
    STATUS       current
    DESCRIPTION
        "Cisco Firepower equipment:POSTCode:method managed
        object property"
    ::= { cfprEquipmentPOSTCodeEntry 8 }

cfprEquipmentPOSTCodeName OBJECT-TYPE
    SYNTAX       SnmpAdminString
    MAX-ACCESS   read-only
    STATUS       current
    DESCRIPTION
        "Cisco Firepower equipment:POSTCode:name managed object property"
    ::= { cfprEquipmentPOSTCodeEntry 9 }

cfprEquipmentPOSTCodeRecoverable OBJECT-TYPE
    SYNTAX       CfprEquipmentPOSTRecoverability
    MAX-ACCESS   read-only
    STATUS       current
    DESCRIPTION
        "Cisco Firepower equipment:POSTCode:recoverable
        managed object property"
    ::= { cfprEquipmentPOSTCodeEntry 10 }

cfprEquipmentPOSTCodeRecoveryAction OBJECT-TYPE
    SYNTAX       SnmpAdminString
    MAX-ACCESS   read-only
    STATUS       current
    DESCRIPTION
        "Cisco Firepower equipment:POSTCode:recoveryAction
        managed object property"
    ::= { cfprEquipmentPOSTCodeEntry 11 }

cfprEquipmentPOSTCodeSeverity OBJECT-TYPE
    SYNTAX       CfprConditionSeverity
    MAX-ACCESS   read-only
    STATUS       current
    DESCRIPTION
        "Cisco Firepower equipment:POSTCode:severity managed
        object property"
    ::= { cfprEquipmentPOSTCodeEntry 12 }

cfprEquipmentPOSTCodeReporterTable OBJECT-TYPE
    SYNTAX           SEQUENCE OF CfprEquipmentPOSTCodeReporterEntry
    MAX-ACCESS       not-accessible
    STATUS           current
    DESCRIPTION
        "Cisco Firepower equipment:POSTCodeReporter managed object table"
    ::= { cfprEquipmentObjects 95 }

cfprEquipmentPOSTCodeReporterEntry OBJECT-TYPE
    SYNTAX           CfprEquipmentPOSTCodeReporterEntry
    MAX-ACCESS       not-accessible
    STATUS           current
    DESCRIPTION
        "Entry for the cfprEquipmentPOSTCodeReporterTable table."
    INDEX { cfprEquipmentPOSTCodeReporterInstanceId }
    ::= { cfprEquipmentPOSTCodeReporterTable 1 }

CfprEquipmentPOSTCodeReporterEntry ::= SEQUENCE {
    cfprEquipmentPOSTCodeReporterInstanceId                          CfprManagedObjectId,
    cfprEquipmentPOSTCodeReporterDn                                  CfprManagedObjectDn,
    cfprEquipmentPOSTCodeReporterRn                                  SnmpAdminString,
    cfprEquipmentPOSTCodeReporterBaseContainer                       SnmpAdminString,
    cfprEquipmentPOSTCodeReporterModel                               SnmpAdminString,
    cfprEquipmentPOSTCodeReporterName                                SnmpAdminString,
    cfprEquipmentPOSTCodeReporterRevision                            SnmpAdminString,
    cfprEquipmentPOSTCodeReporterSerial                              SnmpAdminString,
    cfprEquipmentPOSTCodeReporterType                                SnmpAdminString,
    cfprEquipmentPOSTCodeReporterVendor                              SnmpAdminString
}

cfprEquipmentPOSTCodeReporterInstanceId OBJECT-TYPE
    SYNTAX       CfprManagedObjectId
    MAX-ACCESS   not-accessible
    STATUS       current
    DESCRIPTION
        "Instance identifier of the managed object."
    ::= { cfprEquipmentPOSTCodeReporterEntry 1 }

cfprEquipmentPOSTCodeReporterDn OBJECT-TYPE
    SYNTAX       CfprManagedObjectDn
    MAX-ACCESS   read-only
    STATUS       current
    DESCRIPTION
        "Cisco Firepower equipment:POSTCodeReporter:dn
        managed object property"
    ::= { cfprEquipmentPOSTCodeReporterEntry 2 }

cfprEquipmentPOSTCodeReporterRn OBJECT-TYPE
    SYNTAX       SnmpAdminString
    MAX-ACCESS   read-only
    STATUS       current
    DESCRIPTION
        "Cisco Firepower equipment:POSTCodeReporter:rn
        managed object property"
    ::= { cfprEquipmentPOSTCodeReporterEntry 3 }

cfprEquipmentPOSTCodeReporterBaseContainer OBJECT-TYPE
    SYNTAX       SnmpAdminString
    MAX-ACCESS   read-only
    STATUS       current
    DESCRIPTION
        "Cisco Firepower equipment:POSTCodeReporter:baseContainer
        managed object property"
    ::= { cfprEquipmentPOSTCodeReporterEntry 4 }

cfprEquipmentPOSTCodeReporterModel OBJECT-TYPE
    SYNTAX       SnmpAdminString
    MAX-ACCESS   read-only
    STATUS       current
    DESCRIPTION
        "Cisco Firepower equipment:POSTCodeReporter:model
        managed object property"
    ::= { cfprEquipmentPOSTCodeReporterEntry 5 }

cfprEquipmentPOSTCodeReporterName OBJECT-TYPE
    SYNTAX       SnmpAdminString
    MAX-ACCESS   read-only
    STATUS       current
    DESCRIPTION
        "Cisco Firepower equipment:POSTCodeReporter:name
        managed object property"
    ::= { cfprEquipmentPOSTCodeReporterEntry 6 }

cfprEquipmentPOSTCodeReporterRevision OBJECT-TYPE
    SYNTAX       SnmpAdminString
    MAX-ACCESS   read-only
    STATUS       current
    DESCRIPTION
        "Cisco Firepower equipment:POSTCodeReporter:revision
        managed object property"
    ::= { cfprEquipmentPOSTCodeReporterEntry 7 }

cfprEquipmentPOSTCodeReporterSerial OBJECT-TYPE
    SYNTAX       SnmpAdminString
    MAX-ACCESS   read-only
    STATUS       current
    DESCRIPTION
        "Cisco Firepower equipment:POSTCodeReporter:serial
        managed object property"
    ::= { cfprEquipmentPOSTCodeReporterEntry 8 }

cfprEquipmentPOSTCodeReporterType OBJECT-TYPE
    SYNTAX       SnmpAdminString
    MAX-ACCESS   read-only
    STATUS       current
    DESCRIPTION
        "Cisco Firepower equipment:POSTCodeReporter:type
        managed object property"
    ::= { cfprEquipmentPOSTCodeReporterEntry 9 }

cfprEquipmentPOSTCodeReporterVendor OBJECT-TYPE
    SYNTAX       SnmpAdminString
    MAX-ACCESS   read-only
    STATUS       current
    DESCRIPTION
        "Cisco Firepower equipment:POSTCodeReporter:vendor
        managed object property"
    ::= { cfprEquipmentPOSTCodeReporterEntry 10 }

cfprEquipmentPOSTCodeTemplateTable OBJECT-TYPE
    SYNTAX           SEQUENCE OF CfprEquipmentPOSTCodeTemplateEntry
    MAX-ACCESS       not-accessible
    STATUS           current
    DESCRIPTION
        "Cisco Firepower equipment:POSTCodeTemplate managed object table"
    ::= { cfprEquipmentObjects 96 }

cfprEquipmentPOSTCodeTemplateEntry OBJECT-TYPE
    SYNTAX           CfprEquipmentPOSTCodeTemplateEntry
    MAX-ACCESS       not-accessible
    STATUS           current
    DESCRIPTION
        "Entry for the cfprEquipmentPOSTCodeTemplateTable table."
    INDEX { cfprEquipmentPOSTCodeTemplateInstanceId }
    ::= { cfprEquipmentPOSTCodeTemplateTable 1 }

CfprEquipmentPOSTCodeTemplateEntry ::= SEQUENCE {
    cfprEquipmentPOSTCodeTemplateInstanceId                          CfprManagedObjectId,
    cfprEquipmentPOSTCodeTemplateDn                                  CfprManagedObjectDn,
    cfprEquipmentPOSTCodeTemplateRn                                  SnmpAdminString,
    cfprEquipmentPOSTCodeTemplateBaseContainer                       SnmpAdminString,
    cfprEquipmentPOSTCodeTemplateName                                SnmpAdminString
}

cfprEquipmentPOSTCodeTemplateInstanceId OBJECT-TYPE
    SYNTAX       CfprManagedObjectId
    MAX-ACCESS   not-accessible
    STATUS       current
    DESCRIPTION
        "Instance identifier of the managed object."
    ::= { cfprEquipmentPOSTCodeTemplateEntry 1 }

cfprEquipmentPOSTCodeTemplateDn OBJECT-TYPE
    SYNTAX       CfprManagedObjectDn
    MAX-ACCESS   read-only
    STATUS       current
    DESCRIPTION
        "Cisco Firepower equipment:POSTCodeTemplate:dn
        managed object property"
    ::= { cfprEquipmentPOSTCodeTemplateEntry 2 }

cfprEquipmentPOSTCodeTemplateRn OBJECT-TYPE
    SYNTAX       SnmpAdminString
    MAX-ACCESS   read-only
    STATUS       current
    DESCRIPTION
        "Cisco Firepower equipment:POSTCodeTemplate:rn
        managed object property"
    ::= { cfprEquipmentPOSTCodeTemplateEntry 3 }

cfprEquipmentPOSTCodeTemplateBaseContainer OBJECT-TYPE
    SYNTAX       SnmpAdminString
    MAX-ACCESS   read-only
    STATUS       current
    DESCRIPTION
        "Cisco Firepower equipment:POSTCodeTemplate:baseContainer
        managed object property"
    ::= { cfprEquipmentPOSTCodeTemplateEntry 4 }

cfprEquipmentPOSTCodeTemplateName OBJECT-TYPE
    SYNTAX       SnmpAdminString
    MAX-ACCESS   read-only
    STATUS       current
    DESCRIPTION
        "Cisco Firepower equipment:POSTCodeTemplate:name
        managed object property"
    ::= { cfprEquipmentPOSTCodeTemplateEntry 5 }

cfprEquipmentPciDefTable OBJECT-TYPE
    SYNTAX           SEQUENCE OF CfprEquipmentPciDefEntry
    MAX-ACCESS       not-accessible
    STATUS           current
    DESCRIPTION
        "Cisco Firepower equipment:PciDef managed object table"
    ::= { cfprEquipmentObjects 97 }

cfprEquipmentPciDefEntry OBJECT-TYPE
    SYNTAX           CfprEquipmentPciDefEntry
    MAX-ACCESS       not-accessible
    STATUS           current
    DESCRIPTION
        "Entry for the cfprEquipmentPciDefTable table."
    INDEX { cfprEquipmentPciDefInstanceId }
    ::= { cfprEquipmentPciDefTable 1 }

CfprEquipmentPciDefEntry ::= SEQUENCE {
    cfprEquipmentPciDefInstanceId                                    CfprManagedObjectId,
    cfprEquipmentPciDefDn                                            CfprManagedObjectDn,
    cfprEquipmentPciDefRn                                            SnmpAdminString,
    cfprEquipmentPciDefDescr                                         SnmpAdminString,
    cfprEquipmentPciDefDevice                                        Gauge32,
    cfprEquipmentPciDefIntId                                         SnmpAdminString,
    cfprEquipmentPciDefName                                          SnmpAdminString,
    cfprEquipmentPciDefPolicyLevel                                   Gauge32,
    cfprEquipmentPciDefPolicyOwner                                   CfprPolicyPolicyOwner,
    cfprEquipmentPciDefSubdevice                                     Gauge32,
    cfprEquipmentPciDefSubvendor                                     Gauge32,
    cfprEquipmentPciDefVendor                                        Gauge32
}

cfprEquipmentPciDefInstanceId OBJECT-TYPE
    SYNTAX       CfprManagedObjectId
    MAX-ACCESS   not-accessible
    STATUS       current
    DESCRIPTION
        "Instance identifier of the managed object."
    ::= { cfprEquipmentPciDefEntry 1 }

cfprEquipmentPciDefDn OBJECT-TYPE
    SYNTAX       CfprManagedObjectDn
    MAX-ACCESS   read-only
    STATUS       current
    DESCRIPTION
        "Cisco Firepower equipment:PciDef:dn managed object property"
    ::= { cfprEquipmentPciDefEntry 2 }

cfprEquipmentPciDefRn OBJECT-TYPE
    SYNTAX       SnmpAdminString
    MAX-ACCESS   read-only
    STATUS       current
    DESCRIPTION
        "Cisco Firepower equipment:PciDef:rn managed object property"
    ::= { cfprEquipmentPciDefEntry 3 }

cfprEquipmentPciDefDescr OBJECT-TYPE
    SYNTAX       SnmpAdminString
    MAX-ACCESS   read-only
    STATUS       current
    DESCRIPTION
        "Cisco Firepower equipment:PciDef:descr managed object property"
    ::= { cfprEquipmentPciDefEntry 4 }

cfprEquipmentPciDefDevice OBJECT-TYPE
    SYNTAX       Gauge32
    MAX-ACCESS   read-only
    STATUS       current
    DESCRIPTION
        "Cisco Firepower equipment:PciDef:device managed object property"
    ::= { cfprEquipmentPciDefEntry 5 }

cfprEquipmentPciDefIntId OBJECT-TYPE
    SYNTAX       SnmpAdminString
    MAX-ACCESS   read-only
    STATUS       current
    DESCRIPTION
        "Cisco Firepower equipment:PciDef:intId managed object property"
    ::= { cfprEquipmentPciDefEntry 6 }

cfprEquipmentPciDefName OBJECT-TYPE
    SYNTAX       SnmpAdminString
    MAX-ACCESS   read-only
    STATUS       current
    DESCRIPTION
        "Cisco Firepower equipment:PciDef:name managed object property"
    ::= { cfprEquipmentPciDefEntry 7 }

cfprEquipmentPciDefPolicyLevel OBJECT-TYPE
    SYNTAX       Gauge32
    MAX-ACCESS   read-only
    STATUS       current
    DESCRIPTION
        "Cisco Firepower equipment:PciDef:policyLevel managed
        object property"
    ::= { cfprEquipmentPciDefEntry 8 }

cfprEquipmentPciDefPolicyOwner OBJECT-TYPE
    SYNTAX       CfprPolicyPolicyOwner
    MAX-ACCESS   read-only
    STATUS       current
    DESCRIPTION
        "Cisco Firepower equipment:PciDef:policyOwner managed
        object property"
    ::= { cfprEquipmentPciDefEntry 9 }

cfprEquipmentPciDefSubdevice OBJECT-TYPE
    SYNTAX       Gauge32
    MAX-ACCESS   read-only
    STATUS       current
    DESCRIPTION
        "Cisco Firepower equipment:PciDef:subdevice managed
        object property"
    ::= { cfprEquipmentPciDefEntry 10 }

cfprEquipmentPciDefSubvendor OBJECT-TYPE
    SYNTAX       Gauge32
    MAX-ACCESS   read-only
    STATUS       current
    DESCRIPTION
        "Cisco Firepower equipment:PciDef:subvendor managed
        object property"
    ::= { cfprEquipmentPciDefEntry 11 }

cfprEquipmentPciDefVendor OBJECT-TYPE
    SYNTAX       Gauge32
    MAX-ACCESS   read-only
    STATUS       current
    DESCRIPTION
        "Cisco Firepower equipment:PciDef:vendor managed object property"
    ::= { cfprEquipmentPciDefEntry 12 }

cfprEquipmentPhysDevicesPerBoardTable OBJECT-TYPE
    SYNTAX           SEQUENCE OF CfprEquipmentPhysDevicesPerBoardEntry
    MAX-ACCESS       not-accessible
    STATUS           current
    DESCRIPTION
        "Cisco Firepower equipment:PhysDevicesPerBoard
        managed object table"
    ::= { cfprEquipmentObjects 98 }

cfprEquipmentPhysDevicesPerBoardEntry OBJECT-TYPE
    SYNTAX           CfprEquipmentPhysDevicesPerBoardEntry
    MAX-ACCESS       not-accessible
    STATUS           current
    DESCRIPTION
        "Entry for the cfprEquipmentPhysDevicesPerBoardTable table."
    INDEX { cfprEquipmentPhysDevicesPerBoardInstanceId }
    ::= { cfprEquipmentPhysDevicesPerBoardTable 1 }

CfprEquipmentPhysDevicesPerBoardEntry ::= SEQUENCE {
    cfprEquipmentPhysDevicesPerBoardInstanceId                       CfprManagedObjectId,
    cfprEquipmentPhysDevicesPerBoardDn                               CfprManagedObjectDn,
    cfprEquipmentPhysDevicesPerBoardRn                               SnmpAdminString,
    cfprEquipmentPhysDevicesPerBoardNumOfCpu                         Gauge32,
    cfprEquipmentPhysDevicesPerBoardNumOfDimm                        Gauge32,
    cfprEquipmentPhysDevicesPerBoardNumOfLocalDisk                   Gauge32,
    cfprEquipmentPhysDevicesPerBoardNumOfStorageController           Gauge32,
    cfprEquipmentPhysDevicesPerBoardNumOfadaptor                     Gauge32
}

cfprEquipmentPhysDevicesPerBoardInstanceId OBJECT-TYPE
    SYNTAX       CfprManagedObjectId
    MAX-ACCESS   not-accessible
    STATUS       current
    DESCRIPTION
        "Instance identifier of the managed object."
    ::= { cfprEquipmentPhysDevicesPerBoardEntry 1 }

cfprEquipmentPhysDevicesPerBoardDn OBJECT-TYPE
    SYNTAX       CfprManagedObjectDn
    MAX-ACCESS   read-only
    STATUS       current
    DESCRIPTION
        "Cisco Firepower equipment:PhysDevicesPerBoard:dn
        managed object property"
    ::= { cfprEquipmentPhysDevicesPerBoardEntry 2 }

cfprEquipmentPhysDevicesPerBoardRn OBJECT-TYPE
    SYNTAX       SnmpAdminString
    MAX-ACCESS   read-only
    STATUS       current
    DESCRIPTION
        "Cisco Firepower equipment:PhysDevicesPerBoard:rn
        managed object property"
    ::= { cfprEquipmentPhysDevicesPerBoardEntry 3 }

cfprEquipmentPhysDevicesPerBoardNumOfCpu OBJECT-TYPE
    SYNTAX       Gauge32
    MAX-ACCESS   read-only
    STATUS       current
    DESCRIPTION
        "Cisco Firepower equipment:PhysDevicesPerBoard:numOfCpu
        managed object property"
    ::= { cfprEquipmentPhysDevicesPerBoardEntry 4 }

cfprEquipmentPhysDevicesPerBoardNumOfDimm OBJECT-TYPE
    SYNTAX       Gauge32
    MAX-ACCESS   read-only
    STATUS       current
    DESCRIPTION
        "Cisco Firepower equipment:PhysDevicesPerBoard:numOfDimm
        managed object property"
    ::= { cfprEquipmentPhysDevicesPerBoardEntry 5 }

cfprEquipmentPhysDevicesPerBoardNumOfLocalDisk OBJECT-TYPE
    SYNTAX       Gauge32
    MAX-ACCESS   read-only
    STATUS       current
    DESCRIPTION
        "Cisco Firepower equipment:PhysDevicesPerBoard:numOfLocalDisk
        managed object property"
    ::= { cfprEquipmentPhysDevicesPerBoardEntry 6 }

cfprEquipmentPhysDevicesPerBoardNumOfStorageController OBJECT-TYPE
    SYNTAX       Gauge32
    MAX-ACCESS   read-only
    STATUS       current
    DESCRIPTION
        "Cisco Firepower equipment:PhysDevicesPerBoard:numOfStorageControl
        ler managed object property"
    ::= { cfprEquipmentPhysDevicesPerBoardEntry 7 }

cfprEquipmentPhysDevicesPerBoardNumOfadaptor OBJECT-TYPE
    SYNTAX       Gauge32
    MAX-ACCESS   read-only
    STATUS       current
    DESCRIPTION
        "Cisco Firepower equipment:PhysDevicesPerBoard:numOfadaptor
        managed object property"
    ::= { cfprEquipmentPhysDevicesPerBoardEntry 8 }

cfprEquipmentPhysicalDefTable OBJECT-TYPE
    SYNTAX           SEQUENCE OF CfprEquipmentPhysicalDefEntry
    MAX-ACCESS       not-accessible
    STATUS           current
    DESCRIPTION
        "Cisco Firepower equipment:PhysicalDef managed object table"
    ::= { cfprEquipmentObjects 99 }

cfprEquipmentPhysicalDefEntry OBJECT-TYPE
    SYNTAX           CfprEquipmentPhysicalDefEntry
    MAX-ACCESS       not-accessible
    STATUS           current
    DESCRIPTION
        "Entry for the cfprEquipmentPhysicalDefTable table."
    INDEX { cfprEquipmentPhysicalDefInstanceId }
    ::= { cfprEquipmentPhysicalDefTable 1 }

CfprEquipmentPhysicalDefEntry ::= SEQUENCE {
    cfprEquipmentPhysicalDefInstanceId                               CfprManagedObjectId,
    cfprEquipmentPhysicalDefDn                                       CfprManagedObjectDn,
    cfprEquipmentPhysicalDefRn                                       SnmpAdminString,
    cfprEquipmentPhysicalDefDepth                                    INTEGER,
    cfprEquipmentPhysicalDefDescr                                    SnmpAdminString,
    cfprEquipmentPhysicalDefHeight                                   INTEGER,
    cfprEquipmentPhysicalDefIntId                                    SnmpAdminString,
    cfprEquipmentPhysicalDefMaximumPower                             INTEGER,
    cfprEquipmentPhysicalDefMaximumTemperature                       INTEGER,
    cfprEquipmentPhysicalDefMinimumPower                             INTEGER,
    cfprEquipmentPhysicalDefMinimumTemperature                       INTEGER,
    cfprEquipmentPhysicalDefName                                     SnmpAdminString,
    cfprEquipmentPhysicalDefNominalPower                             INTEGER,
    cfprEquipmentPhysicalDefNominalTemperature                       INTEGER,
    cfprEquipmentPhysicalDefOperatingVoltages                        SnmpAdminString,
    cfprEquipmentPhysicalDefPolicyLevel                              Gauge32,
    cfprEquipmentPhysicalDefPolicyOwner                              CfprPolicyPolicyOwner,
    cfprEquipmentPhysicalDefWeight                                   INTEGER,
    cfprEquipmentPhysicalDefWidth                                    INTEGER
}

cfprEquipmentPhysicalDefInstanceId OBJECT-TYPE
    SYNTAX       CfprManagedObjectId
    MAX-ACCESS   not-accessible
    STATUS       current
    DESCRIPTION
        "Instance identifier of the managed object."
    ::= { cfprEquipmentPhysicalDefEntry 1 }

cfprEquipmentPhysicalDefDn OBJECT-TYPE
    SYNTAX       CfprManagedObjectDn
    MAX-ACCESS   read-only
    STATUS       current
    DESCRIPTION
        "Cisco Firepower equipment:PhysicalDef:dn managed object property"
    ::= { cfprEquipmentPhysicalDefEntry 2 }

cfprEquipmentPhysicalDefRn OBJECT-TYPE
    SYNTAX       SnmpAdminString
    MAX-ACCESS   read-only
    STATUS       current
    DESCRIPTION
        "Cisco Firepower equipment:PhysicalDef:rn managed object property"
    ::= { cfprEquipmentPhysicalDefEntry 3 }

cfprEquipmentPhysicalDefDepth OBJECT-TYPE
    SYNTAX       INTEGER
    MAX-ACCESS   read-only
    STATUS       current
    DESCRIPTION
        "Cisco Firepower equipment:PhysicalDef:depth managed
        object property"
    ::= { cfprEquipmentPhysicalDefEntry 4 }

cfprEquipmentPhysicalDefDescr OBJECT-TYPE
    SYNTAX       SnmpAdminString
    MAX-ACCESS   read-only
    STATUS       current
    DESCRIPTION
        "Cisco Firepower equipment:PhysicalDef:descr managed
        object property"
    ::= { cfprEquipmentPhysicalDefEntry 5 }

cfprEquipmentPhysicalDefHeight OBJECT-TYPE
    SYNTAX       INTEGER
    MAX-ACCESS   read-only
    STATUS       current
    DESCRIPTION
        "Cisco Firepower equipment:PhysicalDef:height managed
        object property"
    ::= { cfprEquipmentPhysicalDefEntry 6 }

cfprEquipmentPhysicalDefIntId OBJECT-TYPE
    SYNTAX       SnmpAdminString
    MAX-ACCESS   read-only
    STATUS       current
    DESCRIPTION
        "Cisco Firepower equipment:PhysicalDef:intId managed
        object property"
    ::= { cfprEquipmentPhysicalDefEntry 7 }

cfprEquipmentPhysicalDefMaximumPower OBJECT-TYPE
    SYNTAX       INTEGER
    MAX-ACCESS   read-only
    STATUS       current
    DESCRIPTION
        "Cisco Firepower equipment:PhysicalDef:maximumPower
        managed object property"
    ::= { cfprEquipmentPhysicalDefEntry 8 }

cfprEquipmentPhysicalDefMaximumTemperature OBJECT-TYPE
    SYNTAX       INTEGER
    MAX-ACCESS   read-only
    STATUS       current
    DESCRIPTION
        "Cisco Firepower equipment:PhysicalDef:maximumTemperature
        managed object property"
    ::= { cfprEquipmentPhysicalDefEntry 9 }

cfprEquipmentPhysicalDefMinimumPower OBJECT-TYPE
    SYNTAX       INTEGER
    MAX-ACCESS   read-only
    STATUS       current
    DESCRIPTION
        "Cisco Firepower equipment:PhysicalDef:minimumPower
        managed object property"
    ::= { cfprEquipmentPhysicalDefEntry 10 }

cfprEquipmentPhysicalDefMinimumTemperature OBJECT-TYPE
    SYNTAX       INTEGER
    MAX-ACCESS   read-only
    STATUS       current
    DESCRIPTION
        "Cisco Firepower equipment:PhysicalDef:minimumTemperature
        managed object property"
    ::= { cfprEquipmentPhysicalDefEntry 11 }

cfprEquipmentPhysicalDefName OBJECT-TYPE
    SYNTAX       SnmpAdminString
    MAX-ACCESS   read-only
    STATUS       current
    DESCRIPTION
        "Cisco Firepower equipment:PhysicalDef:name managed
        object property"
    ::= { cfprEquipmentPhysicalDefEntry 12 }

cfprEquipmentPhysicalDefNominalPower OBJECT-TYPE
    SYNTAX       INTEGER
    MAX-ACCESS   read-only
    STATUS       current
    DESCRIPTION
        "Cisco Firepower equipment:PhysicalDef:nominalPower
        managed object property"
    ::= { cfprEquipmentPhysicalDefEntry 13 }

cfprEquipmentPhysicalDefNominalTemperature OBJECT-TYPE
    SYNTAX       INTEGER
    MAX-ACCESS   read-only
    STATUS       current
    DESCRIPTION
        "Cisco Firepower equipment:PhysicalDef:nominalTemperature
        managed object property"
    ::= { cfprEquipmentPhysicalDefEntry 14 }

cfprEquipmentPhysicalDefOperatingVoltages OBJECT-TYPE
    SYNTAX       SnmpAdminString
    MAX-ACCESS   read-only
    STATUS       current
    DESCRIPTION
        "Cisco Firepower equipment:PhysicalDef:operatingVoltages
        managed object property"
    ::= { cfprEquipmentPhysicalDefEntry 15 }

cfprEquipmentPhysicalDefPolicyLevel OBJECT-TYPE
    SYNTAX       Gauge32
    MAX-ACCESS   read-only
    STATUS       current
    DESCRIPTION
        "Cisco Firepower equipment:PhysicalDef:policyLevel
        managed object property"
    ::= { cfprEquipmentPhysicalDefEntry 16 }

cfprEquipmentPhysicalDefPolicyOwner OBJECT-TYPE
    SYNTAX       CfprPolicyPolicyOwner
    MAX-ACCESS   read-only
    STATUS       current
    DESCRIPTION
        "Cisco Firepower equipment:PhysicalDef:policyOwner
        managed object property"
    ::= { cfprEquipmentPhysicalDefEntry 17 }

cfprEquipmentPhysicalDefWeight OBJECT-TYPE
    SYNTAX       INTEGER
    MAX-ACCESS   read-only
    STATUS       current
    DESCRIPTION
        "Cisco Firepower equipment:PhysicalDef:weight managed
        object property"
    ::= { cfprEquipmentPhysicalDefEntry 18 }

cfprEquipmentPhysicalDefWidth OBJECT-TYPE
    SYNTAX       INTEGER
    MAX-ACCESS   read-only
    STATUS       current
    DESCRIPTION
        "Cisco Firepower equipment:PhysicalDef:width managed
        object property"
    ::= { cfprEquipmentPhysicalDefEntry 19 }

cfprEquipmentPictureTable OBJECT-TYPE
    SYNTAX           SEQUENCE OF CfprEquipmentPictureEntry
    MAX-ACCESS       not-accessible
    STATUS           current
    DESCRIPTION
        "Cisco Firepower equipment:Picture managed object table"
    ::= { cfprEquipmentObjects 100 }

cfprEquipmentPictureEntry OBJECT-TYPE
    SYNTAX           CfprEquipmentPictureEntry
    MAX-ACCESS       not-accessible
    STATUS           current
    DESCRIPTION
        "Entry for the cfprEquipmentPictureTable table."
    INDEX { cfprEquipmentPictureInstanceId }
    ::= { cfprEquipmentPictureTable 1 }

CfprEquipmentPictureEntry ::= SEQUENCE {
    cfprEquipmentPictureInstanceId                                   CfprManagedObjectId,
    cfprEquipmentPictureDn                                           CfprManagedObjectDn,
    cfprEquipmentPictureRn                                           SnmpAdminString,
    cfprEquipmentPictureFileName                                     SnmpAdminString,
    cfprEquipmentPictureType                                         CfprEquipmentPictureType
}

cfprEquipmentPictureInstanceId OBJECT-TYPE
    SYNTAX       CfprManagedObjectId
    MAX-ACCESS   not-accessible
    STATUS       current
    DESCRIPTION
        "Instance identifier of the managed object."
    ::= { cfprEquipmentPictureEntry 1 }

cfprEquipmentPictureDn OBJECT-TYPE
    SYNTAX       CfprManagedObjectDn
    MAX-ACCESS   read-only
    STATUS       current
    DESCRIPTION
        "Cisco Firepower equipment:Picture:dn managed object property"
    ::= { cfprEquipmentPictureEntry 2 }

cfprEquipmentPictureRn OBJECT-TYPE
    SYNTAX       SnmpAdminString
    MAX-ACCESS   read-only
    STATUS       current
    DESCRIPTION
        "Cisco Firepower equipment:Picture:rn managed object property"
    ::= { cfprEquipmentPictureEntry 3 }

cfprEquipmentPictureFileName OBJECT-TYPE
    SYNTAX       SnmpAdminString
    MAX-ACCESS   read-only
    STATUS       current
    DESCRIPTION
        "Cisco Firepower equipment:Picture:fileName managed
        object property"
    ::= { cfprEquipmentPictureEntry 4 }

cfprEquipmentPictureType OBJECT-TYPE
    SYNTAX       CfprEquipmentPictureType
    MAX-ACCESS   read-only
    STATUS       current
    DESCRIPTION
        "Cisco Firepower equipment:Picture:type managed object property"
    ::= { cfprEquipmentPictureEntry 5 }

cfprEquipmentPortCapTable OBJECT-TYPE
    SYNTAX           SEQUENCE OF CfprEquipmentPortCapEntry
    MAX-ACCESS       not-accessible
    STATUS           current
    DESCRIPTION
        "Cisco Firepower equipment:PortCap managed object table"
    ::= { cfprEquipmentObjects 101 }

cfprEquipmentPortCapEntry OBJECT-TYPE
    SYNTAX           CfprEquipmentPortCapEntry
    MAX-ACCESS       not-accessible
    STATUS           current
    DESCRIPTION
        "Entry for the cfprEquipmentPortCapTable table."
    INDEX { cfprEquipmentPortCapInstanceId }
    ::= { cfprEquipmentPortCapTable 1 }

CfprEquipmentPortCapEntry ::= SEQUENCE {
    cfprEquipmentPortCapInstanceId                                   CfprManagedObjectId,
    cfprEquipmentPortCapDn                                           CfprManagedObjectDn,
    cfprEquipmentPortCapRn                                           SnmpAdminString,
    cfprEquipmentPortCapBreakoutPortSpeedGb                          Gauge32,
    cfprEquipmentPortCapCountBreakoutPorts                           Gauge32,
    cfprEquipmentPortCapDescr                                        SnmpAdminString,
    cfprEquipmentPortCapEndPortId                                    Gauge32,
    cfprEquipmentPortCapIntId                                        SnmpAdminString,
    cfprEquipmentPortCapName                                         SnmpAdminString,
    cfprEquipmentPortCapPolicyLevel                                  Gauge32,
    cfprEquipmentPortCapPolicyOwner                                  CfprPolicyPolicyOwner,
    cfprEquipmentPortCapPortAttribute                                CfprEquipmentPortAttribute,
    cfprEquipmentPortCapPortSpeedGb                                  Gauge32,
    cfprEquipmentPortCapStartPortId                                  Gauge32,
    cfprEquipmentPortCapMediaType                                    CfprEquipmentMediaType,
    cfprEquipmentPortCapPortSpeedCap                                 CfprEquipmentEthPortSpeedCap
}

cfprEquipmentPortCapInstanceId OBJECT-TYPE
    SYNTAX       CfprManagedObjectId
    MAX-ACCESS   not-accessible
    STATUS       current
    DESCRIPTION
        "Instance identifier of the managed object."
    ::= { cfprEquipmentPortCapEntry 1 }

cfprEquipmentPortCapDn OBJECT-TYPE
    SYNTAX       CfprManagedObjectDn
    MAX-ACCESS   read-only
    STATUS       current
    DESCRIPTION
        "Cisco Firepower equipment:PortCap:dn managed object property"
    ::= { cfprEquipmentPortCapEntry 2 }

cfprEquipmentPortCapRn OBJECT-TYPE
    SYNTAX       SnmpAdminString
    MAX-ACCESS   read-only
    STATUS       current
    DESCRIPTION
        "Cisco Firepower equipment:PortCap:rn managed object property"
    ::= { cfprEquipmentPortCapEntry 3 }

cfprEquipmentPortCapBreakoutPortSpeedGb OBJECT-TYPE
    SYNTAX       Gauge32
    MAX-ACCESS   read-only
    STATUS       current
    DESCRIPTION
        "Cisco Firepower equipment:PortCap:breakoutPortSpeedGb
        managed object property"
    ::= { cfprEquipmentPortCapEntry 4 }

cfprEquipmentPortCapCountBreakoutPorts OBJECT-TYPE
    SYNTAX       Gauge32
    MAX-ACCESS   read-only
    STATUS       current
    DESCRIPTION
        "Cisco Firepower equipment:PortCap:countBreakoutPorts
        managed object property"
    ::= { cfprEquipmentPortCapEntry 5 }

cfprEquipmentPortCapDescr OBJECT-TYPE
    SYNTAX       SnmpAdminString
    MAX-ACCESS   read-only
    STATUS       current
    DESCRIPTION
        "Cisco Firepower equipment:PortCap:descr managed object property"
    ::= { cfprEquipmentPortCapEntry 6 }

cfprEquipmentPortCapEndPortId OBJECT-TYPE
    SYNTAX       Gauge32
    MAX-ACCESS   read-only
    STATUS       current
    DESCRIPTION
        "Cisco Firepower equipment:PortCap:endPortId managed
        object property"
    ::= { cfprEquipmentPortCapEntry 7 }

cfprEquipmentPortCapIntId OBJECT-TYPE
    SYNTAX       SnmpAdminString
    MAX-ACCESS   read-only
    STATUS       current
    DESCRIPTION
        "Cisco Firepower equipment:PortCap:intId managed object property"
    ::= { cfprEquipmentPortCapEntry 8 }

cfprEquipmentPortCapName OBJECT-TYPE
    SYNTAX       SnmpAdminString
    MAX-ACCESS   read-only
    STATUS       current
    DESCRIPTION
        "Cisco Firepower equipment:PortCap:name managed object property"
    ::= { cfprEquipmentPortCapEntry 9 }

cfprEquipmentPortCapPolicyLevel OBJECT-TYPE
    SYNTAX       Gauge32
    MAX-ACCESS   read-only
    STATUS       current
    DESCRIPTION
        "Cisco Firepower equipment:PortCap:policyLevel
        managed object property"
    ::= { cfprEquipmentPortCapEntry 10 }

cfprEquipmentPortCapPolicyOwner OBJECT-TYPE
    SYNTAX       CfprPolicyPolicyOwner
    MAX-ACCESS   read-only
    STATUS       current
    DESCRIPTION
        "Cisco Firepower equipment:PortCap:policyOwner
        managed object property"
    ::= { cfprEquipmentPortCapEntry 11 }

cfprEquipmentPortCapPortAttribute OBJECT-TYPE
    SYNTAX       CfprEquipmentPortAttribute
    MAX-ACCESS   read-only
    STATUS       current
    DESCRIPTION
        "Cisco Firepower equipment:PortCap:portAttribute
        managed object property"
    ::= { cfprEquipmentPortCapEntry 12 }

cfprEquipmentPortCapPortSpeedGb OBJECT-TYPE
    SYNTAX       Gauge32
    MAX-ACCESS   read-only
    STATUS       current
    DESCRIPTION
        "Cisco Firepower equipment:PortCap:portSpeedGb
        managed object property"
    ::= { cfprEquipmentPortCapEntry 13 }

cfprEquipmentPortCapStartPortId OBJECT-TYPE
    SYNTAX       Gauge32
    MAX-ACCESS   read-only
    STATUS       current
    DESCRIPTION
        "Cisco Firepower equipment:PortCap:startPortId
        managed object property"
    ::= { cfprEquipmentPortCapEntry 14 }

cfprEquipmentPortCapMediaType OBJECT-TYPE
    SYNTAX       CfprEquipmentMediaType
    MAX-ACCESS   read-only
    STATUS       current
    DESCRIPTION
        "Cisco Firepower equipment:PortCap:mediaType managed
        object property"
    ::= { cfprEquipmentPortCapEntry 15 }

cfprEquipmentPortCapPortSpeedCap OBJECT-TYPE
    SYNTAX       CfprEquipmentEthPortSpeedCap
    MAX-ACCESS   read-only
    STATUS       current
    DESCRIPTION
        "Cisco Firepower equipment:PortCap:portSpeedCap
        managed object property"
    ::= { cfprEquipmentPortCapEntry 16 }

cfprEquipmentPortGroupAggregationDefTable OBJECT-TYPE
    SYNTAX           SEQUENCE OF CfprEquipmentPortGroupAggregationDefEntry
    MAX-ACCESS       not-accessible
    STATUS           current
    DESCRIPTION
        "Cisco Firepower equipment:PortGroupAggregationDef
        managed object table"
    ::= { cfprEquipmentObjects 102 }

cfprEquipmentPortGroupAggregationDefEntry OBJECT-TYPE
    SYNTAX           CfprEquipmentPortGroupAggregationDefEntry
    MAX-ACCESS       not-accessible
    STATUS           current
    DESCRIPTION
        "Entry for the cfprEquipmentPortGroupAggregationDefTable table."
    INDEX { cfprEquipmentPortGroupAggregationDefInstanceId }
    ::= { cfprEquipmentPortGroupAggregationDefTable 1 }

CfprEquipmentPortGroupAggregationDefEntry ::= SEQUENCE {
    cfprEquipmentPortGroupAggregationDefInstanceId                   CfprManagedObjectId,
    cfprEquipmentPortGroupAggregationDefDn                           CfprManagedObjectDn,
    cfprEquipmentPortGroupAggregationDefRn                           SnmpAdminString,
    cfprEquipmentPortGroupAggregationDefAggregationCap               CfprComputeLinkAggregationCap,
    cfprEquipmentPortGroupAggregationDefDescr                        SnmpAdminString,
    cfprEquipmentPortGroupAggregationDefIntId                        SnmpAdminString,
    cfprEquipmentPortGroupAggregationDefName                         SnmpAdminString,
    cfprEquipmentPortGroupAggregationDefPolicyLevel                  Gauge32,
    cfprEquipmentPortGroupAggregationDefPolicyOwner                  CfprPolicyPolicyOwner,
    cfprEquipmentPortGroupAggregationDefType                         CfprPortGroupType
}

cfprEquipmentPortGroupAggregationDefInstanceId OBJECT-TYPE
    SYNTAX       CfprManagedObjectId
    MAX-ACCESS   not-accessible
    STATUS       current
    DESCRIPTION
        "Instance identifier of the managed object."
    ::= { cfprEquipmentPortGroupAggregationDefEntry 1 }

cfprEquipmentPortGroupAggregationDefDn OBJECT-TYPE
    SYNTAX       CfprManagedObjectDn
    MAX-ACCESS   read-only
    STATUS       current
    DESCRIPTION
        "Cisco Firepower equipment:PortGroupAggregationDef:dn
        managed object property"
    ::= { cfprEquipmentPortGroupAggregationDefEntry 2 }

cfprEquipmentPortGroupAggregationDefRn OBJECT-TYPE
    SYNTAX       SnmpAdminString
    MAX-ACCESS   read-only
    STATUS       current
    DESCRIPTION
        "Cisco Firepower equipment:PortGroupAggregationDef:rn
        managed object property"
    ::= { cfprEquipmentPortGroupAggregationDefEntry 3 }

cfprEquipmentPortGroupAggregationDefAggregationCap OBJECT-TYPE
    SYNTAX       CfprComputeLinkAggregationCap
    MAX-ACCESS   read-only
    STATUS       current
    DESCRIPTION
        "Cisco Firepower equipment:PortGroupAggregationDef:aggregationCap
        managed object property"
    ::= { cfprEquipmentPortGroupAggregationDefEntry 4 }

cfprEquipmentPortGroupAggregationDefDescr OBJECT-TYPE
    SYNTAX       SnmpAdminString
    MAX-ACCESS   read-only
    STATUS       current
    DESCRIPTION
        "Cisco Firepower equipment:PortGroupAggregationDef:descr
        managed object property"
    ::= { cfprEquipmentPortGroupAggregationDefEntry 5 }

cfprEquipmentPortGroupAggregationDefIntId OBJECT-TYPE
    SYNTAX       SnmpAdminString
    MAX-ACCESS   read-only
    STATUS       current
    DESCRIPTION
        "Cisco Firepower equipment:PortGroupAggregationDef:intId
        managed object property"
    ::= { cfprEquipmentPortGroupAggregationDefEntry 6 }

cfprEquipmentPortGroupAggregationDefName OBJECT-TYPE
    SYNTAX       SnmpAdminString
    MAX-ACCESS   read-only
    STATUS       current
    DESCRIPTION
        "Cisco Firepower equipment:PortGroupAggregationDef:name
        managed object property"
    ::= { cfprEquipmentPortGroupAggregationDefEntry 7 }

cfprEquipmentPortGroupAggregationDefPolicyLevel OBJECT-TYPE
    SYNTAX       Gauge32
    MAX-ACCESS   read-only
    STATUS       current
    DESCRIPTION
        "Cisco Firepower equipment:PortGroupAggregationDef:policyLevel
        managed object property"
    ::= { cfprEquipmentPortGroupAggregationDefEntry 8 }

cfprEquipmentPortGroupAggregationDefPolicyOwner OBJECT-TYPE
    SYNTAX       CfprPolicyPolicyOwner
    MAX-ACCESS   read-only
    STATUS       current
    DESCRIPTION
        "Cisco Firepower equipment:PortGroupAggregationDef:policyOwner
        managed object property"
    ::= { cfprEquipmentPortGroupAggregationDefEntry 9 }

cfprEquipmentPortGroupAggregationDefType OBJECT-TYPE
    SYNTAX       CfprPortGroupType
    MAX-ACCESS   read-only
    STATUS       current
    DESCRIPTION
        "Cisco Firepower equipment:PortGroupAggregationDef:type
        managed object property"
    ::= { cfprEquipmentPortGroupAggregationDefEntry 10 }

cfprEquipmentPortGroupDefTable OBJECT-TYPE
    SYNTAX           SEQUENCE OF CfprEquipmentPortGroupDefEntry
    MAX-ACCESS       not-accessible
    STATUS           current
    DESCRIPTION
        "Cisco Firepower equipment:PortGroupDef managed object table"
    ::= { cfprEquipmentObjects 103 }

cfprEquipmentPortGroupDefEntry OBJECT-TYPE
    SYNTAX           CfprEquipmentPortGroupDefEntry
    MAX-ACCESS       not-accessible
    STATUS           current
    DESCRIPTION
        "Entry for the cfprEquipmentPortGroupDefTable table."
    INDEX { cfprEquipmentPortGroupDefInstanceId }
    ::= { cfprEquipmentPortGroupDefTable 1 }

CfprEquipmentPortGroupDefEntry ::= SEQUENCE {
    cfprEquipmentPortGroupDefInstanceId                              CfprManagedObjectId,
    cfprEquipmentPortGroupDefDn                                      CfprManagedObjectDn,
    cfprEquipmentPortGroupDefRn                                      SnmpAdminString,
    cfprEquipmentPortGroupDefDescr                                   SnmpAdminString,
    cfprEquipmentPortGroupDefIntId                                   SnmpAdminString,
    cfprEquipmentPortGroupDefName                                    SnmpAdminString,
    cfprEquipmentPortGroupDefNumberOfPorts                           Gauge32,
    cfprEquipmentPortGroupDefPolicyLevel                             Gauge32,
    cfprEquipmentPortGroupDefPolicyOwner                             CfprPolicyPolicyOwner,
    cfprEquipmentPortGroupDefStartPortId                             Gauge32,
    cfprEquipmentPortGroupDefType                                    CfprPortGroupType
}

cfprEquipmentPortGroupDefInstanceId OBJECT-TYPE
    SYNTAX       CfprManagedObjectId
    MAX-ACCESS   not-accessible
    STATUS       current
    DESCRIPTION
        "Instance identifier of the managed object."
    ::= { cfprEquipmentPortGroupDefEntry 1 }

cfprEquipmentPortGroupDefDn OBJECT-TYPE
    SYNTAX       CfprManagedObjectDn
    MAX-ACCESS   read-only
    STATUS       current
    DESCRIPTION
        "Cisco Firepower equipment:PortGroupDef:dn managed
        object property"
    ::= { cfprEquipmentPortGroupDefEntry 2 }

cfprEquipmentPortGroupDefRn OBJECT-TYPE
    SYNTAX       SnmpAdminString
    MAX-ACCESS   read-only
    STATUS       current
    DESCRIPTION
        "Cisco Firepower equipment:PortGroupDef:rn managed
        object property"
    ::= { cfprEquipmentPortGroupDefEntry 3 }

cfprEquipmentPortGroupDefDescr OBJECT-TYPE
    SYNTAX       SnmpAdminString
    MAX-ACCESS   read-only
    STATUS       current
    DESCRIPTION
        "Cisco Firepower equipment:PortGroupDef:descr managed
        object property"
    ::= { cfprEquipmentPortGroupDefEntry 4 }

cfprEquipmentPortGroupDefIntId OBJECT-TYPE
    SYNTAX       SnmpAdminString
    MAX-ACCESS   read-only
    STATUS       current
    DESCRIPTION
        "Cisco Firepower equipment:PortGroupDef:intId managed
        object property"
    ::= { cfprEquipmentPortGroupDefEntry 5 }

cfprEquipmentPortGroupDefName OBJECT-TYPE
    SYNTAX       SnmpAdminString
    MAX-ACCESS   read-only
    STATUS       current
    DESCRIPTION
        "Cisco Firepower equipment:PortGroupDef:name managed
        object property"
    ::= { cfprEquipmentPortGroupDefEntry 6 }

cfprEquipmentPortGroupDefNumberOfPorts OBJECT-TYPE
    SYNTAX       Gauge32
    MAX-ACCESS   read-only
    STATUS       current
    DESCRIPTION
        "Cisco Firepower equipment:PortGroupDef:numberOfPorts
        managed object property"
    ::= { cfprEquipmentPortGroupDefEntry 7 }

cfprEquipmentPortGroupDefPolicyLevel OBJECT-TYPE
    SYNTAX       Gauge32
    MAX-ACCESS   read-only
    STATUS       current
    DESCRIPTION
        "Cisco Firepower equipment:PortGroupDef:policyLevel
        managed object property"
    ::= { cfprEquipmentPortGroupDefEntry 8 }

cfprEquipmentPortGroupDefPolicyOwner OBJECT-TYPE
    SYNTAX       CfprPolicyPolicyOwner
    MAX-ACCESS   read-only
    STATUS       current
    DESCRIPTION
        "Cisco Firepower equipment:PortGroupDef:policyOwner
        managed object property"
    ::= { cfprEquipmentPortGroupDefEntry 9 }

cfprEquipmentPortGroupDefStartPortId OBJECT-TYPE
    SYNTAX       Gauge32
    MAX-ACCESS   read-only
    STATUS       current
    DESCRIPTION
        "Cisco Firepower equipment:PortGroupDef:startPortId
        managed object property"
    ::= { cfprEquipmentPortGroupDefEntry 10 }

cfprEquipmentPortGroupDefType OBJECT-TYPE
    SYNTAX       CfprPortGroupType
    MAX-ACCESS   read-only
    STATUS       current
    DESCRIPTION
        "Cisco Firepower equipment:PortGroupDef:type managed
        object property"
    ::= { cfprEquipmentPortGroupDefEntry 11 }

cfprEquipmentPortGroupSwComplexDefTable OBJECT-TYPE
    SYNTAX           SEQUENCE OF CfprEquipmentPortGroupSwComplexDefEntry
    MAX-ACCESS       not-accessible
    STATUS           current
    DESCRIPTION
        "Cisco Firepower equipment:PortGroupSwComplexDef
        managed object table"
    ::= { cfprEquipmentObjects 104 }

cfprEquipmentPortGroupSwComplexDefEntry OBJECT-TYPE
    SYNTAX           CfprEquipmentPortGroupSwComplexDefEntry
    MAX-ACCESS       not-accessible
    STATUS           current
    DESCRIPTION
        "Entry for the cfprEquipmentPortGroupSwComplexDefTable table."
    INDEX { cfprEquipmentPortGroupSwComplexDefInstanceId }
    ::= { cfprEquipmentPortGroupSwComplexDefTable 1 }

CfprEquipmentPortGroupSwComplexDefEntry ::= SEQUENCE {
    cfprEquipmentPortGroupSwComplexDefInstanceId                     CfprManagedObjectId,
    cfprEquipmentPortGroupSwComplexDefDn                             CfprManagedObjectDn,
    cfprEquipmentPortGroupSwComplexDefRn                             SnmpAdminString,
    cfprEquipmentPortGroupSwComplexDefAsic                           CfprEquipmentAsicType,
    cfprEquipmentPortGroupSwComplexDefDescr                          SnmpAdminString,
    cfprEquipmentPortGroupSwComplexDefIntId                          SnmpAdminString,
    cfprEquipmentPortGroupSwComplexDefName                           SnmpAdminString,
    cfprEquipmentPortGroupSwComplexDefPolicyLevel                    Gauge32,
    cfprEquipmentPortGroupSwComplexDefPolicyOwner                    CfprPolicyPolicyOwner,
    cfprEquipmentPortGroupSwComplexDefPortCapacity                   Gauge32,
    cfprEquipmentPortGroupSwComplexDefSwComplexCapacity              Gauge32,
    cfprEquipmentPortGroupSwComplexDefVifCapacity                    Gauge32
}

cfprEquipmentPortGroupSwComplexDefInstanceId OBJECT-TYPE
    SYNTAX       CfprManagedObjectId
    MAX-ACCESS   not-accessible
    STATUS       current
    DESCRIPTION
        "Instance identifier of the managed object."
    ::= { cfprEquipmentPortGroupSwComplexDefEntry 1 }

cfprEquipmentPortGroupSwComplexDefDn OBJECT-TYPE
    SYNTAX       CfprManagedObjectDn
    MAX-ACCESS   read-only
    STATUS       current
    DESCRIPTION
        "Cisco Firepower equipment:PortGroupSwComplexDef:dn
        managed object property"
    ::= { cfprEquipmentPortGroupSwComplexDefEntry 2 }

cfprEquipmentPortGroupSwComplexDefRn OBJECT-TYPE
    SYNTAX       SnmpAdminString
    MAX-ACCESS   read-only
    STATUS       current
    DESCRIPTION
        "Cisco Firepower equipment:PortGroupSwComplexDef:rn
        managed object property"
    ::= { cfprEquipmentPortGroupSwComplexDefEntry 3 }

cfprEquipmentPortGroupSwComplexDefAsic OBJECT-TYPE
    SYNTAX       CfprEquipmentAsicType
    MAX-ACCESS   read-only
    STATUS       current
    DESCRIPTION
        "Cisco Firepower equipment:PortGroupSwComplexDef:asic
        managed object property"
    ::= { cfprEquipmentPortGroupSwComplexDefEntry 4 }

cfprEquipmentPortGroupSwComplexDefDescr OBJECT-TYPE
    SYNTAX       SnmpAdminString
    MAX-ACCESS   read-only
    STATUS       current
    DESCRIPTION
        "Cisco Firepower equipment:PortGroupSwComplexDef:descr
        managed object property"
    ::= { cfprEquipmentPortGroupSwComplexDefEntry 5 }

cfprEquipmentPortGroupSwComplexDefIntId OBJECT-TYPE
    SYNTAX       SnmpAdminString
    MAX-ACCESS   read-only
    STATUS       current
    DESCRIPTION
        "Cisco Firepower equipment:PortGroupSwComplexDef:intId
        managed object property"
    ::= { cfprEquipmentPortGroupSwComplexDefEntry 6 }

cfprEquipmentPortGroupSwComplexDefName OBJECT-TYPE
    SYNTAX       SnmpAdminString
    MAX-ACCESS   read-only
    STATUS       current
    DESCRIPTION
        "Cisco Firepower equipment:PortGroupSwComplexDef:name
        managed object property"
    ::= { cfprEquipmentPortGroupSwComplexDefEntry 7 }

cfprEquipmentPortGroupSwComplexDefPolicyLevel OBJECT-TYPE
    SYNTAX       Gauge32
    MAX-ACCESS   read-only
    STATUS       current
    DESCRIPTION
        "Cisco Firepower equipment:PortGroupSwComplexDef:policyLevel
        managed object property"
    ::= { cfprEquipmentPortGroupSwComplexDefEntry 8 }

cfprEquipmentPortGroupSwComplexDefPolicyOwner OBJECT-TYPE
    SYNTAX       CfprPolicyPolicyOwner
    MAX-ACCESS   read-only
    STATUS       current
    DESCRIPTION
        "Cisco Firepower equipment:PortGroupSwComplexDef:policyOwner
        managed object property"
    ::= { cfprEquipmentPortGroupSwComplexDefEntry 9 }

cfprEquipmentPortGroupSwComplexDefPortCapacity OBJECT-TYPE
    SYNTAX       Gauge32
    MAX-ACCESS   read-only
    STATUS       current
    DESCRIPTION
        "Cisco Firepower equipment:PortGroupSwComplexDef:portCapacity
        managed object property"
    ::= { cfprEquipmentPortGroupSwComplexDefEntry 10 }

cfprEquipmentPortGroupSwComplexDefSwComplexCapacity OBJECT-TYPE
    SYNTAX       Gauge32
    MAX-ACCESS   read-only
    STATUS       current
    DESCRIPTION
        "Cisco Firepower equipment:PortGroupSwComplexDef:swComplexCapacity
         managed object property"
    ::= { cfprEquipmentPortGroupSwComplexDefEntry 11 }

cfprEquipmentPortGroupSwComplexDefVifCapacity OBJECT-TYPE
    SYNTAX       Gauge32
    MAX-ACCESS   read-only
    STATUS       current
    DESCRIPTION
        "Cisco Firepower equipment:PortGroupSwComplexDef:vifCapacity
        managed object property"
    ::= { cfprEquipmentPortGroupSwComplexDefEntry 12 }

cfprEquipmentPortSwComplexRefTable OBJECT-TYPE
    SYNTAX           SEQUENCE OF CfprEquipmentPortSwComplexRefEntry
    MAX-ACCESS       not-accessible
    STATUS           current
    DESCRIPTION
        "Cisco Firepower equipment:PortSwComplexRef managed object table"
    ::= { cfprEquipmentObjects 105 }

cfprEquipmentPortSwComplexRefEntry OBJECT-TYPE
    SYNTAX           CfprEquipmentPortSwComplexRefEntry
    MAX-ACCESS       not-accessible
    STATUS           current
    DESCRIPTION
        "Entry for the cfprEquipmentPortSwComplexRefTable table."
    INDEX { cfprEquipmentPortSwComplexRefInstanceId }
    ::= { cfprEquipmentPortSwComplexRefTable 1 }

CfprEquipmentPortSwComplexRefEntry ::= SEQUENCE {
    cfprEquipmentPortSwComplexRefInstanceId                          CfprManagedObjectId,
    cfprEquipmentPortSwComplexRefDn                                  CfprManagedObjectDn,
    cfprEquipmentPortSwComplexRefRn                                  SnmpAdminString,
    cfprEquipmentPortSwComplexRefDescr                               SnmpAdminString,
    cfprEquipmentPortSwComplexRefIntId                               SnmpAdminString,
    cfprEquipmentPortSwComplexRefMaxPortId                           Gauge32,
    cfprEquipmentPortSwComplexRefMinPortId                           Gauge32,
    cfprEquipmentPortSwComplexRefName                                SnmpAdminString,
    cfprEquipmentPortSwComplexRefPolicyLevel                         Gauge32,
    cfprEquipmentPortSwComplexRefPolicyOwner                         CfprPolicyPolicyOwner,
    cfprEquipmentPortSwComplexRefSlotId                              Gauge32,
    cfprEquipmentPortSwComplexRefSwComplexId                         Gauge32
}

cfprEquipmentPortSwComplexRefInstanceId OBJECT-TYPE
    SYNTAX       CfprManagedObjectId
    MAX-ACCESS   not-accessible
    STATUS       current
    DESCRIPTION
        "Instance identifier of the managed object."
    ::= { cfprEquipmentPortSwComplexRefEntry 1 }

cfprEquipmentPortSwComplexRefDn OBJECT-TYPE
    SYNTAX       CfprManagedObjectDn
    MAX-ACCESS   read-only
    STATUS       current
    DESCRIPTION
        "Cisco Firepower equipment:PortSwComplexRef:dn
        managed object property"
    ::= { cfprEquipmentPortSwComplexRefEntry 2 }

cfprEquipmentPortSwComplexRefRn OBJECT-TYPE
    SYNTAX       SnmpAdminString
    MAX-ACCESS   read-only
    STATUS       current
    DESCRIPTION
        "Cisco Firepower equipment:PortSwComplexRef:rn
        managed object property"
    ::= { cfprEquipmentPortSwComplexRefEntry 3 }

cfprEquipmentPortSwComplexRefDescr OBJECT-TYPE
    SYNTAX       SnmpAdminString
    MAX-ACCESS   read-only
    STATUS       current
    DESCRIPTION
        "Cisco Firepower equipment:PortSwComplexRef:descr
        managed object property"
    ::= { cfprEquipmentPortSwComplexRefEntry 4 }

cfprEquipmentPortSwComplexRefIntId OBJECT-TYPE
    SYNTAX       SnmpAdminString
    MAX-ACCESS   read-only
    STATUS       current
    DESCRIPTION
        "Cisco Firepower equipment:PortSwComplexRef:intId
        managed object property"
    ::= { cfprEquipmentPortSwComplexRefEntry 5 }

cfprEquipmentPortSwComplexRefMaxPortId OBJECT-TYPE
    SYNTAX       Gauge32
    MAX-ACCESS   read-only
    STATUS       current
    DESCRIPTION
        "Cisco Firepower equipment:PortSwComplexRef:maxPortId
        managed object property"
    ::= { cfprEquipmentPortSwComplexRefEntry 6 }

cfprEquipmentPortSwComplexRefMinPortId OBJECT-TYPE
    SYNTAX       Gauge32
    MAX-ACCESS   read-only
    STATUS       current
    DESCRIPTION
        "Cisco Firepower equipment:PortSwComplexRef:minPortId
        managed object property"
    ::= { cfprEquipmentPortSwComplexRefEntry 7 }

cfprEquipmentPortSwComplexRefName OBJECT-TYPE
    SYNTAX       SnmpAdminString
    MAX-ACCESS   read-only
    STATUS       current
    DESCRIPTION
        "Cisco Firepower equipment:PortSwComplexRef:name
        managed object property"
    ::= { cfprEquipmentPortSwComplexRefEntry 8 }

cfprEquipmentPortSwComplexRefPolicyLevel OBJECT-TYPE
    SYNTAX       Gauge32
    MAX-ACCESS   read-only
    STATUS       current
    DESCRIPTION
        "Cisco Firepower equipment:PortSwComplexRef:policyLevel
        managed object property"
    ::= { cfprEquipmentPortSwComplexRefEntry 9 }

cfprEquipmentPortSwComplexRefPolicyOwner OBJECT-TYPE
    SYNTAX       CfprPolicyPolicyOwner
    MAX-ACCESS   read-only
    STATUS       current
    DESCRIPTION
        "Cisco Firepower equipment:PortSwComplexRef:policyOwner
        managed object property"
    ::= { cfprEquipmentPortSwComplexRefEntry 10 }

cfprEquipmentPortSwComplexRefSlotId OBJECT-TYPE
    SYNTAX       Gauge32
    MAX-ACCESS   read-only
    STATUS       current
    DESCRIPTION
        "Cisco Firepower equipment:PortSwComplexRef:slotId
        managed object property"
    ::= { cfprEquipmentPortSwComplexRefEntry 11 }

cfprEquipmentPortSwComplexRefSwComplexId OBJECT-TYPE
    SYNTAX       Gauge32
    MAX-ACCESS   read-only
    STATUS       current
    DESCRIPTION
        "Cisco Firepower equipment:PortSwComplexRef:swComplexId
        managed object property"
    ::= { cfprEquipmentPortSwComplexRefEntry 12 }

cfprEquipmentPowerCapDefTable OBJECT-TYPE
    SYNTAX           SEQUENCE OF CfprEquipmentPowerCapDefEntry
    MAX-ACCESS       not-accessible
    STATUS           current
    DESCRIPTION
        "Cisco Firepower equipment:PowerCapDef managed object table"
    ::= { cfprEquipmentObjects 106 }

cfprEquipmentPowerCapDefEntry OBJECT-TYPE
    SYNTAX           CfprEquipmentPowerCapDefEntry
    MAX-ACCESS       not-accessible
    STATUS           current
    DESCRIPTION
        "Entry for the cfprEquipmentPowerCapDefTable table."
    INDEX { cfprEquipmentPowerCapDefInstanceId }
    ::= { cfprEquipmentPowerCapDefTable 1 }

CfprEquipmentPowerCapDefEntry ::= SEQUENCE {
    cfprEquipmentPowerCapDefInstanceId                               CfprManagedObjectId,
    cfprEquipmentPowerCapDefDn                                       CfprManagedObjectDn,
    cfprEquipmentPowerCapDefRn                                       SnmpAdminString,
    cfprEquipmentPowerCapDefMinBiosVersion                           SnmpAdminString,
    cfprEquipmentPowerCapDefMinCimcVersion                           SnmpAdminString,
    cfprEquipmentPowerCapDefMinCmcVersion                            SnmpAdminString,
    cfprEquipmentPowerCapDefProfileMethod                            CfprEquipmentPowerCapDefProfileMethod
}

cfprEquipmentPowerCapDefInstanceId OBJECT-TYPE
    SYNTAX       CfprManagedObjectId
    MAX-ACCESS   not-accessible
    STATUS       current
    DESCRIPTION
        "Instance identifier of the managed object."
    ::= { cfprEquipmentPowerCapDefEntry 1 }

cfprEquipmentPowerCapDefDn OBJECT-TYPE
    SYNTAX       CfprManagedObjectDn
    MAX-ACCESS   read-only
    STATUS       current
    DESCRIPTION
        "Cisco Firepower equipment:PowerCapDef:dn managed object property"
    ::= { cfprEquipmentPowerCapDefEntry 2 }

cfprEquipmentPowerCapDefRn OBJECT-TYPE
    SYNTAX       SnmpAdminString
    MAX-ACCESS   read-only
    STATUS       current
    DESCRIPTION
        "Cisco Firepower equipment:PowerCapDef:rn managed object property"
    ::= { cfprEquipmentPowerCapDefEntry 3 }

cfprEquipmentPowerCapDefMinBiosVersion OBJECT-TYPE
    SYNTAX       SnmpAdminString
    MAX-ACCESS   read-only
    STATUS       current
    DESCRIPTION
        "Cisco Firepower equipment:PowerCapDef:minBiosVersion
        managed object property"
    ::= { cfprEquipmentPowerCapDefEntry 4 }

cfprEquipmentPowerCapDefMinCimcVersion OBJECT-TYPE
    SYNTAX       SnmpAdminString
    MAX-ACCESS   read-only
    STATUS       current
    DESCRIPTION
        "Cisco Firepower equipment:PowerCapDef:minCimcVersion
        managed object property"
    ::= { cfprEquipmentPowerCapDefEntry 5 }

cfprEquipmentPowerCapDefMinCmcVersion OBJECT-TYPE
    SYNTAX       SnmpAdminString
    MAX-ACCESS   read-only
    STATUS       current
    DESCRIPTION
        "Cisco Firepower equipment:PowerCapDef:minCmcVersion
        managed object property"
    ::= { cfprEquipmentPowerCapDefEntry 6 }

cfprEquipmentPowerCapDefProfileMethod OBJECT-TYPE
    SYNTAX       CfprEquipmentPowerCapDefProfileMethod
    MAX-ACCESS   read-only
    STATUS       current
    DESCRIPTION
        "Cisco Firepower equipment:PowerCapDef:profileMethod
        managed object property"
    ::= { cfprEquipmentPowerCapDefEntry 7 }

cfprEquipmentProcessorUnitCapProviderTable OBJECT-TYPE
    SYNTAX           SEQUENCE OF CfprEquipmentProcessorUnitCapProviderEntry
    MAX-ACCESS       not-accessible
    STATUS           current
    DESCRIPTION
        "Cisco Firepower equipment:ProcessorUnitCapProvider
        managed object table"
    ::= { cfprEquipmentObjects 107 }

cfprEquipmentProcessorUnitCapProviderEntry OBJECT-TYPE
    SYNTAX           CfprEquipmentProcessorUnitCapProviderEntry
    MAX-ACCESS       not-accessible
    STATUS           current
    DESCRIPTION
        "Entry for the cfprEquipmentProcessorUnitCapProviderTable table."
    INDEX { cfprEquipmentProcessorUnitCapProviderInstanceId }
    ::= { cfprEquipmentProcessorUnitCapProviderTable 1 }

CfprEquipmentProcessorUnitCapProviderEntry ::= SEQUENCE {
    cfprEquipmentProcessorUnitCapProviderInstanceId                  CfprManagedObjectId,
    cfprEquipmentProcessorUnitCapProviderDn                          CfprManagedObjectDn,
    cfprEquipmentProcessorUnitCapProviderRn                          SnmpAdminString,
    cfprEquipmentProcessorUnitCapProviderDeleted                     TruthValue,
    cfprEquipmentProcessorUnitCapProviderDeprecated                  TruthValue,
    cfprEquipmentProcessorUnitCapProviderElementLoadFailures         Gauge32,
    cfprEquipmentProcessorUnitCapProviderElementsLoaded              Gauge32,
    cfprEquipmentProcessorUnitCapProviderGencount                    Gauge32,
    cfprEquipmentProcessorUnitCapProviderLoadErrors                  Gauge32,
    cfprEquipmentProcessorUnitCapProviderLoadWarnings                Gauge32,
    cfprEquipmentProcessorUnitCapProviderMgmtPlaneVer                SnmpAdminString,
    cfprEquipmentProcessorUnitCapProviderModel                       SnmpAdminString,
    cfprEquipmentProcessorUnitCapProviderPromCardType                Gauge32,
    cfprEquipmentProcessorUnitCapProviderRevision                    SnmpAdminString,
    cfprEquipmentProcessorUnitCapProviderVendor                      SnmpAdminString
}

cfprEquipmentProcessorUnitCapProviderInstanceId OBJECT-TYPE
    SYNTAX       CfprManagedObjectId
    MAX-ACCESS   not-accessible
    STATUS       current
    DESCRIPTION
        "Instance identifier of the managed object."
    ::= { cfprEquipmentProcessorUnitCapProviderEntry 1 }

cfprEquipmentProcessorUnitCapProviderDn OBJECT-TYPE
    SYNTAX       CfprManagedObjectDn
    MAX-ACCESS   read-only
    STATUS       current
    DESCRIPTION
        "Cisco Firepower equipment:ProcessorUnitCapProvider:dn
        managed object property"
    ::= { cfprEquipmentProcessorUnitCapProviderEntry 2 }

cfprEquipmentProcessorUnitCapProviderRn OBJECT-TYPE
    SYNTAX       SnmpAdminString
    MAX-ACCESS   read-only
    STATUS       current
    DESCRIPTION
        "Cisco Firepower equipment:ProcessorUnitCapProvider:rn
        managed object property"
    ::= { cfprEquipmentProcessorUnitCapProviderEntry 3 }

cfprEquipmentProcessorUnitCapProviderDeleted OBJECT-TYPE
    SYNTAX       TruthValue
    MAX-ACCESS   read-only
    STATUS       current
    DESCRIPTION
        "Cisco Firepower equipment:ProcessorUnitCapProvider:deleted
        managed object property"
    ::= { cfprEquipmentProcessorUnitCapProviderEntry 4 }

cfprEquipmentProcessorUnitCapProviderDeprecated OBJECT-TYPE
    SYNTAX       TruthValue
    MAX-ACCESS   read-only
    STATUS       current
    DESCRIPTION
        "Cisco Firepower equipment:ProcessorUnitCapProvider:deprecated
        managed object property"
    ::= { cfprEquipmentProcessorUnitCapProviderEntry 5 }

cfprEquipmentProcessorUnitCapProviderElementLoadFailures OBJECT-TYPE
    SYNTAX       Gauge32
    MAX-ACCESS   read-only
    STATUS       current
    DESCRIPTION
        "Cisco Firepower equipment:ProcessorUnitCapProvider:elementLoadFai
        lures managed object property"
    ::= { cfprEquipmentProcessorUnitCapProviderEntry 6 }

cfprEquipmentProcessorUnitCapProviderElementsLoaded OBJECT-TYPE
    SYNTAX       Gauge32
    MAX-ACCESS   read-only
    STATUS       current
    DESCRIPTION
        "Cisco Firepower equipment:ProcessorUnitCapProvider:elementsLoaded
         managed object property"
    ::= { cfprEquipmentProcessorUnitCapProviderEntry 7 }

cfprEquipmentProcessorUnitCapProviderGencount OBJECT-TYPE
    SYNTAX       Gauge32
    MAX-ACCESS   read-only
    STATUS       current
    DESCRIPTION
        "Cisco Firepower equipment:ProcessorUnitCapProvider:gencount
        managed object property"
    ::= { cfprEquipmentProcessorUnitCapProviderEntry 8 }

cfprEquipmentProcessorUnitCapProviderLoadErrors OBJECT-TYPE
    SYNTAX       Gauge32
    MAX-ACCESS   read-only
    STATUS       current
    DESCRIPTION
        "Cisco Firepower equipment:ProcessorUnitCapProvider:loadErrors
        managed object property"
    ::= { cfprEquipmentProcessorUnitCapProviderEntry 9 }

cfprEquipmentProcessorUnitCapProviderLoadWarnings OBJECT-TYPE
    SYNTAX       Gauge32
    MAX-ACCESS   read-only
    STATUS       current
    DESCRIPTION
        "Cisco Firepower equipment:ProcessorUnitCapProvider:loadWarnings
        managed object property"
    ::= { cfprEquipmentProcessorUnitCapProviderEntry 10 }

cfprEquipmentProcessorUnitCapProviderMgmtPlaneVer OBJECT-TYPE
    SYNTAX       SnmpAdminString
    MAX-ACCESS   read-only
    STATUS       current
    DESCRIPTION
        "Cisco Firepower equipment:ProcessorUnitCapProvider:mgmtPlaneVer
        managed object property"
    ::= { cfprEquipmentProcessorUnitCapProviderEntry 11 }

cfprEquipmentProcessorUnitCapProviderModel OBJECT-TYPE
    SYNTAX       SnmpAdminString
    MAX-ACCESS   read-only
    STATUS       current
    DESCRIPTION
        "Cisco Firepower equipment:ProcessorUnitCapProvider:model
        managed object property"
    ::= { cfprEquipmentProcessorUnitCapProviderEntry 12 }

cfprEquipmentProcessorUnitCapProviderPromCardType OBJECT-TYPE
    SYNTAX       Gauge32
    MAX-ACCESS   read-only
    STATUS       current
    DESCRIPTION
        "Cisco Firepower equipment:ProcessorUnitCapProvider:promCardType
        managed object property"
    ::= { cfprEquipmentProcessorUnitCapProviderEntry 13 }

cfprEquipmentProcessorUnitCapProviderRevision OBJECT-TYPE
    SYNTAX       SnmpAdminString
    MAX-ACCESS   read-only
    STATUS       current
    DESCRIPTION
        "Cisco Firepower equipment:ProcessorUnitCapProvider:revision
        managed object property"
    ::= { cfprEquipmentProcessorUnitCapProviderEntry 14 }

cfprEquipmentProcessorUnitCapProviderVendor OBJECT-TYPE
    SYNTAX       SnmpAdminString
    MAX-ACCESS   read-only
    STATUS       current
    DESCRIPTION
        "Cisco Firepower equipment:ProcessorUnitCapProvider:vendor
        managed object property"
    ::= { cfprEquipmentProcessorUnitCapProviderEntry 15 }

cfprEquipmentProcessorUnitDefTable OBJECT-TYPE
    SYNTAX           SEQUENCE OF CfprEquipmentProcessorUnitDefEntry
    MAX-ACCESS       not-accessible
    STATUS           current
    DESCRIPTION
        "Cisco Firepower equipment:ProcessorUnitDef managed object table"
    ::= { cfprEquipmentObjects 108 }

cfprEquipmentProcessorUnitDefEntry OBJECT-TYPE
    SYNTAX           CfprEquipmentProcessorUnitDefEntry
    MAX-ACCESS       not-accessible
    STATUS           current
    DESCRIPTION
        "Entry for the cfprEquipmentProcessorUnitDefTable table."
    INDEX { cfprEquipmentProcessorUnitDefInstanceId }
    ::= { cfprEquipmentProcessorUnitDefTable 1 }

CfprEquipmentProcessorUnitDefEntry ::= SEQUENCE {
    cfprEquipmentProcessorUnitDefInstanceId                          CfprManagedObjectId,
    cfprEquipmentProcessorUnitDefDn                                  CfprManagedObjectDn,
    cfprEquipmentProcessorUnitDefRn                                  SnmpAdminString,
    cfprEquipmentProcessorUnitDefAddressWidth                        Gauge32,
    cfprEquipmentProcessorUnitDefDataWidth                           Gauge32,
    cfprEquipmentProcessorUnitDefDescr                               SnmpAdminString,
    cfprEquipmentProcessorUnitDefIntId                               SnmpAdminString,
    cfprEquipmentProcessorUnitDefMaxSpeed                            INTEGER,
    cfprEquipmentProcessorUnitDefName                                SnmpAdminString,
    cfprEquipmentProcessorUnitDefPolicyLevel                         Gauge32,
    cfprEquipmentProcessorUnitDefPolicyOwner                         CfprPolicyPolicyOwner
}

cfprEquipmentProcessorUnitDefInstanceId OBJECT-TYPE
    SYNTAX       CfprManagedObjectId
    MAX-ACCESS   not-accessible
    STATUS       current
    DESCRIPTION
        "Instance identifier of the managed object."
    ::= { cfprEquipmentProcessorUnitDefEntry 1 }

cfprEquipmentProcessorUnitDefDn OBJECT-TYPE
    SYNTAX       CfprManagedObjectDn
    MAX-ACCESS   read-only
    STATUS       current
    DESCRIPTION
        "Cisco Firepower equipment:ProcessorUnitDef:dn
        managed object property"
    ::= { cfprEquipmentProcessorUnitDefEntry 2 }

cfprEquipmentProcessorUnitDefRn OBJECT-TYPE
    SYNTAX       SnmpAdminString
    MAX-ACCESS   read-only
    STATUS       current
    DESCRIPTION
        "Cisco Firepower equipment:ProcessorUnitDef:rn
        managed object property"
    ::= { cfprEquipmentProcessorUnitDefEntry 3 }

cfprEquipmentProcessorUnitDefAddressWidth OBJECT-TYPE
    SYNTAX       Gauge32
    MAX-ACCESS   read-only
    STATUS       current
    DESCRIPTION
        "Cisco Firepower equipment:ProcessorUnitDef:addressWidth
        managed object property"
    ::= { cfprEquipmentProcessorUnitDefEntry 4 }

cfprEquipmentProcessorUnitDefDataWidth OBJECT-TYPE
    SYNTAX       Gauge32
    MAX-ACCESS   read-only
    STATUS       current
    DESCRIPTION
        "Cisco Firepower equipment:ProcessorUnitDef:dataWidth
        managed object property"
    ::= { cfprEquipmentProcessorUnitDefEntry 5 }

cfprEquipmentProcessorUnitDefDescr OBJECT-TYPE
    SYNTAX       SnmpAdminString
    MAX-ACCESS   read-only
    STATUS       current
    DESCRIPTION
        "Cisco Firepower equipment:ProcessorUnitDef:descr
        managed object property"
    ::= { cfprEquipmentProcessorUnitDefEntry 6 }

cfprEquipmentProcessorUnitDefIntId OBJECT-TYPE
    SYNTAX       SnmpAdminString
    MAX-ACCESS   read-only
    STATUS       current
    DESCRIPTION
        "Cisco Firepower equipment:ProcessorUnitDef:intId
        managed object property"
    ::= { cfprEquipmentProcessorUnitDefEntry 7 }

cfprEquipmentProcessorUnitDefMaxSpeed OBJECT-TYPE
    SYNTAX       INTEGER
    MAX-ACCESS   read-only
    STATUS       current
    DESCRIPTION
        "Cisco Firepower equipment:ProcessorUnitDef:maxSpeed
        managed object property"
    ::= { cfprEquipmentProcessorUnitDefEntry 8 }

cfprEquipmentProcessorUnitDefName OBJECT-TYPE
    SYNTAX       SnmpAdminString
    MAX-ACCESS   read-only
    STATUS       current
    DESCRIPTION
        "Cisco Firepower equipment:ProcessorUnitDef:name
        managed object property"
    ::= { cfprEquipmentProcessorUnitDefEntry 9 }

cfprEquipmentProcessorUnitDefPolicyLevel OBJECT-TYPE
    SYNTAX       Gauge32
    MAX-ACCESS   read-only
    STATUS       current
    DESCRIPTION
        "Cisco Firepower equipment:ProcessorUnitDef:policyLevel
        managed object property"
    ::= { cfprEquipmentProcessorUnitDefEntry 10 }

cfprEquipmentProcessorUnitDefPolicyOwner OBJECT-TYPE
    SYNTAX       CfprPolicyPolicyOwner
    MAX-ACCESS   read-only
    STATUS       current
    DESCRIPTION
        "Cisco Firepower equipment:ProcessorUnitDef:policyOwner
        managed object property"
    ::= { cfprEquipmentProcessorUnitDefEntry 11 }

cfprEquipmentPsuTable OBJECT-TYPE
    SYNTAX           SEQUENCE OF CfprEquipmentPsuEntry
    MAX-ACCESS       not-accessible
    STATUS           current
    DESCRIPTION
        "Cisco Firepower equipment:Psu managed object table"
    ::= { cfprEquipmentObjects 109 }

cfprEquipmentPsuEntry OBJECT-TYPE
    SYNTAX           CfprEquipmentPsuEntry
    MAX-ACCESS       not-accessible
    STATUS           current
    DESCRIPTION
        "Entry for the cfprEquipmentPsuTable table."
    INDEX { cfprEquipmentPsuInstanceId }
    ::= { cfprEquipmentPsuTable 1 }

CfprEquipmentPsuEntry ::= SEQUENCE {
    cfprEquipmentPsuInstanceId                                       CfprManagedObjectId,
    cfprEquipmentPsuDn                                               CfprManagedObjectDn,
    cfprEquipmentPsuRn                                               SnmpAdminString,
    cfprEquipmentPsuType                                             CfprEquipmentPsuType,
    cfprEquipmentPsuFltAggr                                          Unsigned64,
    cfprEquipmentPsuId                                               CfprEquipmentPsuId,
    cfprEquipmentPsuModel                                            SnmpAdminString,
    cfprEquipmentPsuOperQualifierReason                              SnmpAdminString,
    cfprEquipmentPsuOperState                                        CfprEquipmentOperability,
    cfprEquipmentPsuOperability                                      CfprEquipmentOperability,
    cfprEquipmentPsuPartNumber                                       SnmpAdminString,
    cfprEquipmentPsuPerf                                             CfprEquipmentSensorThresholdStatus,
    cfprEquipmentPsuPower                                            CfprEquipmentPowerState,
    cfprEquipmentPsuPowerStateQualifier                              CfprEquipmentPsuStateQualifier,
    cfprEquipmentPsuPresence                                         CfprEquipmentPresence,
    cfprEquipmentPsuPsuFirmwareVersion                               SnmpAdminString,
    cfprEquipmentPsuPsuInputSrc                                      CfprEquipmentPsuInputSrc,
    cfprEquipmentPsuPsuType                                          CfprEquipmentPsuVoltageType,
    cfprEquipmentPsuPsuWattage                                       Gauge32,
    cfprEquipmentPsuRevision                                         SnmpAdminString,
    cfprEquipmentPsuSerial                                           SnmpAdminString,
    cfprEquipmentPsuThermal                                          CfprEquipmentSensorThresholdStatus,
    cfprEquipmentPsuVendor                                           SnmpAdminString,
    cfprEquipmentPsuVid                                              SnmpAdminString,
    cfprEquipmentPsuVoltage                                          CfprEquipmentSensorThresholdStatus
}

cfprEquipmentPsuInstanceId OBJECT-TYPE
    SYNTAX       CfprManagedObjectId
    MAX-ACCESS   not-accessible
    STATUS       current
    DESCRIPTION
        "Instance identifier of the managed object."
    ::= { cfprEquipmentPsuEntry 1 }

cfprEquipmentPsuDn OBJECT-TYPE
    SYNTAX       CfprManagedObjectDn
    MAX-ACCESS   read-only
    STATUS       current
    DESCRIPTION
        "Cisco Firepower equipment:Psu:dn managed object property"
    ::= { cfprEquipmentPsuEntry 2 }

cfprEquipmentPsuRn OBJECT-TYPE
    SYNTAX       SnmpAdminString
    MAX-ACCESS   read-only
    STATUS       current
    DESCRIPTION
        "Cisco Firepower equipment:Psu:rn managed object property"
    ::= { cfprEquipmentPsuEntry 3 }

cfprEquipmentPsuType OBJECT-TYPE
    SYNTAX       CfprEquipmentPsuType
    MAX-ACCESS   read-only
    STATUS       current
    DESCRIPTION
        "Cisco Firepower equipment:Psu:Type managed object property"
    ::= { cfprEquipmentPsuEntry 4 }

cfprEquipmentPsuFltAggr OBJECT-TYPE
    SYNTAX       Unsigned64
    MAX-ACCESS   read-only
    STATUS       current
    DESCRIPTION
        "Cisco Firepower equipment:Psu:fltAggr managed object property"
    ::= { cfprEquipmentPsuEntry 5 }

cfprEquipmentPsuId OBJECT-TYPE
    SYNTAX       CfprEquipmentPsuId
    MAX-ACCESS   read-only
    STATUS       current
    DESCRIPTION
        "Cisco Firepower equipment:Psu:id managed object property"
    ::= { cfprEquipmentPsuEntry 6 }

cfprEquipmentPsuModel OBJECT-TYPE
    SYNTAX       SnmpAdminString
    MAX-ACCESS   read-only
    STATUS       current
    DESCRIPTION
        "Cisco Firepower equipment:Psu:model managed object property"
    ::= { cfprEquipmentPsuEntry 7 }

cfprEquipmentPsuOperQualifierReason OBJECT-TYPE
    SYNTAX       SnmpAdminString
    MAX-ACCESS   read-only
    STATUS       current
    DESCRIPTION
        "Cisco Firepower equipment:Psu:operQualifierReason
        managed object property"
    ::= { cfprEquipmentPsuEntry 8 }

cfprEquipmentPsuOperState OBJECT-TYPE
    SYNTAX       CfprEquipmentOperability
    MAX-ACCESS   read-only
    STATUS       current
    DESCRIPTION
        "Cisco Firepower equipment:Psu:operState managed object property"
    ::= { cfprEquipmentPsuEntry 9 }

cfprEquipmentPsuOperability OBJECT-TYPE
    SYNTAX       CfprEquipmentOperability
    MAX-ACCESS   read-only
    STATUS       current
    DESCRIPTION
        "Cisco Firepower equipment:Psu:operability managed
        object property"
    ::= { cfprEquipmentPsuEntry 10 }

cfprEquipmentPsuPartNumber OBJECT-TYPE
    SYNTAX       SnmpAdminString
    MAX-ACCESS   read-only
    STATUS       current
    DESCRIPTION
        "Cisco Firepower equipment:Psu:partNumber managed object property"
    ::= { cfprEquipmentPsuEntry 11 }

cfprEquipmentPsuPerf OBJECT-TYPE
    SYNTAX       CfprEquipmentSensorThresholdStatus
    MAX-ACCESS   read-only
    STATUS       current
    DESCRIPTION
        "Cisco Firepower equipment:Psu:perf managed object property"
    ::= { cfprEquipmentPsuEntry 12 }

cfprEquipmentPsuPower OBJECT-TYPE
    SYNTAX       CfprEquipmentPowerState
    MAX-ACCESS   read-only
    STATUS       current
    DESCRIPTION
        "Cisco Firepower equipment:Psu:power managed object property"
    ::= { cfprEquipmentPsuEntry 13 }

cfprEquipmentPsuPowerStateQualifier OBJECT-TYPE
    SYNTAX       CfprEquipmentPsuStateQualifier
    MAX-ACCESS   read-only
    STATUS       current
    DESCRIPTION
        "Cisco Firepower equipment:Psu:powerStateQualifier
        managed object property"
    ::= { cfprEquipmentPsuEntry 14 }

cfprEquipmentPsuPresence OBJECT-TYPE
    SYNTAX       CfprEquipmentPresence
    MAX-ACCESS   read-only
    STATUS       current
    DESCRIPTION
        "Cisco Firepower equipment:Psu:presence managed object property"
    ::= { cfprEquipmentPsuEntry 15 }

cfprEquipmentPsuPsuFirmwareVersion OBJECT-TYPE
    SYNTAX       SnmpAdminString
    MAX-ACCESS   read-only
    STATUS       current
    DESCRIPTION
        "Cisco Firepower equipment:Psu:psuFirmwareVersion
        managed object property"
    ::= { cfprEquipmentPsuEntry 16 }

cfprEquipmentPsuPsuInputSrc OBJECT-TYPE
    SYNTAX       CfprEquipmentPsuInputSrc
    MAX-ACCESS   read-only
    STATUS       current
    DESCRIPTION
        "Cisco Firepower equipment:Psu:psuInputSrc managed
        object property"
    ::= { cfprEquipmentPsuEntry 17 }

cfprEquipmentPsuPsuType OBJECT-TYPE
    SYNTAX       CfprEquipmentPsuVoltageType
    MAX-ACCESS   read-only
    STATUS       current
    DESCRIPTION
        "Cisco Firepower equipment:Psu:psuType managed object property"
    ::= { cfprEquipmentPsuEntry 18 }

cfprEquipmentPsuPsuWattage OBJECT-TYPE
    SYNTAX       Gauge32
    MAX-ACCESS   read-only
    STATUS       current
    DESCRIPTION
        "Cisco Firepower equipment:Psu:psuWattage managed object property"
    ::= { cfprEquipmentPsuEntry 19 }

cfprEquipmentPsuRevision OBJECT-TYPE
    SYNTAX       SnmpAdminString
    MAX-ACCESS   read-only
    STATUS       current
    DESCRIPTION
        "Cisco Firepower equipment:Psu:revision managed object property"
    ::= { cfprEquipmentPsuEntry 20 }

cfprEquipmentPsuSerial OBJECT-TYPE
    SYNTAX       SnmpAdminString
    MAX-ACCESS   read-only
    STATUS       current
    DESCRIPTION
        "Cisco Firepower equipment:Psu:serial managed object property"
    ::= { cfprEquipmentPsuEntry 21 }

cfprEquipmentPsuThermal OBJECT-TYPE
    SYNTAX       CfprEquipmentSensorThresholdStatus
    MAX-ACCESS   read-only
    STATUS       current
    DESCRIPTION
        "Cisco Firepower equipment:Psu:thermal managed object property"
    ::= { cfprEquipmentPsuEntry 22 }

cfprEquipmentPsuVendor OBJECT-TYPE
    SYNTAX       SnmpAdminString
    MAX-ACCESS   read-only
    STATUS       current
    DESCRIPTION
        "Cisco Firepower equipment:Psu:vendor managed object property"
    ::= { cfprEquipmentPsuEntry 23 }

cfprEquipmentPsuVid OBJECT-TYPE
    SYNTAX       SnmpAdminString
    MAX-ACCESS   read-only
    STATUS       current
    DESCRIPTION
        "Cisco Firepower equipment:Psu:vid managed object property"
    ::= { cfprEquipmentPsuEntry 24 }

cfprEquipmentPsuVoltage OBJECT-TYPE
    SYNTAX       CfprEquipmentSensorThresholdStatus
    MAX-ACCESS   read-only
    STATUS       current
    DESCRIPTION
        "Cisco Firepower equipment:Psu:voltage managed object property"
    ::= { cfprEquipmentPsuEntry 25 }

cfprEquipmentPsuCapProviderTable OBJECT-TYPE
    SYNTAX           SEQUENCE OF CfprEquipmentPsuCapProviderEntry
    MAX-ACCESS       not-accessible
    STATUS           current
    DESCRIPTION
        "Cisco Firepower equipment:PsuCapProvider managed object table"
    ::= { cfprEquipmentObjects 110 }

cfprEquipmentPsuCapProviderEntry OBJECT-TYPE
    SYNTAX           CfprEquipmentPsuCapProviderEntry
    MAX-ACCESS       not-accessible
    STATUS           current
    DESCRIPTION
        "Entry for the cfprEquipmentPsuCapProviderTable table."
    INDEX { cfprEquipmentPsuCapProviderInstanceId }
    ::= { cfprEquipmentPsuCapProviderTable 1 }

CfprEquipmentPsuCapProviderEntry ::= SEQUENCE {
    cfprEquipmentPsuCapProviderInstanceId                            CfprManagedObjectId,
    cfprEquipmentPsuCapProviderDn                                    CfprManagedObjectDn,
    cfprEquipmentPsuCapProviderRn                                    SnmpAdminString,
    cfprEquipmentPsuCapProviderDeleted                               TruthValue,
    cfprEquipmentPsuCapProviderDeprecated                            TruthValue,
    cfprEquipmentPsuCapProviderElementLoadFailures                   Gauge32,
    cfprEquipmentPsuCapProviderElementsLoaded                        Gauge32,
    cfprEquipmentPsuCapProviderGencount                              Gauge32,
    cfprEquipmentPsuCapProviderLoadErrors                            Gauge32,
    cfprEquipmentPsuCapProviderLoadWarnings                          Gauge32,
    cfprEquipmentPsuCapProviderMgmtPlaneVer                          SnmpAdminString,
    cfprEquipmentPsuCapProviderModel                                 SnmpAdminString,
    cfprEquipmentPsuCapProviderPromCardType                          Gauge32,
    cfprEquipmentPsuCapProviderRevision                              SnmpAdminString,
    cfprEquipmentPsuCapProviderVendor                                SnmpAdminString
}

cfprEquipmentPsuCapProviderInstanceId OBJECT-TYPE
    SYNTAX       CfprManagedObjectId
    MAX-ACCESS   not-accessible
    STATUS       current
    DESCRIPTION
        "Instance identifier of the managed object."
    ::= { cfprEquipmentPsuCapProviderEntry 1 }

cfprEquipmentPsuCapProviderDn OBJECT-TYPE
    SYNTAX       CfprManagedObjectDn
    MAX-ACCESS   read-only
    STATUS       current
    DESCRIPTION
        "Cisco Firepower equipment:PsuCapProvider:dn managed
        object property"
    ::= { cfprEquipmentPsuCapProviderEntry 2 }

cfprEquipmentPsuCapProviderRn OBJECT-TYPE
    SYNTAX       SnmpAdminString
    MAX-ACCESS   read-only
    STATUS       current
    DESCRIPTION
        "Cisco Firepower equipment:PsuCapProvider:rn managed
        object property"
    ::= { cfprEquipmentPsuCapProviderEntry 3 }

cfprEquipmentPsuCapProviderDeleted OBJECT-TYPE
    SYNTAX       TruthValue
    MAX-ACCESS   read-only
    STATUS       current
    DESCRIPTION
        "Cisco Firepower equipment:PsuCapProvider:deleted
        managed object property"
    ::= { cfprEquipmentPsuCapProviderEntry 4 }

cfprEquipmentPsuCapProviderDeprecated OBJECT-TYPE
    SYNTAX       TruthValue
    MAX-ACCESS   read-only
    STATUS       current
    DESCRIPTION
        "Cisco Firepower equipment:PsuCapProvider:deprecated
        managed object property"
    ::= { cfprEquipmentPsuCapProviderEntry 5 }

cfprEquipmentPsuCapProviderElementLoadFailures OBJECT-TYPE
    SYNTAX       Gauge32
    MAX-ACCESS   read-only
    STATUS       current
    DESCRIPTION
        "Cisco Firepower equipment:PsuCapProvider:elementLoadFailures
        managed object property"
    ::= { cfprEquipmentPsuCapProviderEntry 6 }

cfprEquipmentPsuCapProviderElementsLoaded OBJECT-TYPE
    SYNTAX       Gauge32
    MAX-ACCESS   read-only
    STATUS       current
    DESCRIPTION
        "Cisco Firepower equipment:PsuCapProvider:elementsLoaded
        managed object property"
    ::= { cfprEquipmentPsuCapProviderEntry 7 }

cfprEquipmentPsuCapProviderGencount OBJECT-TYPE
    SYNTAX       Gauge32
    MAX-ACCESS   read-only
    STATUS       current
    DESCRIPTION
        "Cisco Firepower equipment:PsuCapProvider:gencount
        managed object property"
    ::= { cfprEquipmentPsuCapProviderEntry 8 }

cfprEquipmentPsuCapProviderLoadErrors OBJECT-TYPE
    SYNTAX       Gauge32
    MAX-ACCESS   read-only
    STATUS       current
    DESCRIPTION
        "Cisco Firepower equipment:PsuCapProvider:loadErrors
        managed object property"
    ::= { cfprEquipmentPsuCapProviderEntry 9 }

cfprEquipmentPsuCapProviderLoadWarnings OBJECT-TYPE
    SYNTAX       Gauge32
    MAX-ACCESS   read-only
    STATUS       current
    DESCRIPTION
        "Cisco Firepower equipment:PsuCapProvider:loadWarnings
        managed object property"
    ::= { cfprEquipmentPsuCapProviderEntry 10 }

cfprEquipmentPsuCapProviderMgmtPlaneVer OBJECT-TYPE
    SYNTAX       SnmpAdminString
    MAX-ACCESS   read-only
    STATUS       current
    DESCRIPTION
        "Cisco Firepower equipment:PsuCapProvider:mgmtPlaneVer
        managed object property"
    ::= { cfprEquipmentPsuCapProviderEntry 11 }

cfprEquipmentPsuCapProviderModel OBJECT-TYPE
    SYNTAX       SnmpAdminString
    MAX-ACCESS   read-only
    STATUS       current
    DESCRIPTION
        "Cisco Firepower equipment:PsuCapProvider:model
        managed object property"
    ::= { cfprEquipmentPsuCapProviderEntry 12 }

cfprEquipmentPsuCapProviderPromCardType OBJECT-TYPE
    SYNTAX       Gauge32
    MAX-ACCESS   read-only
    STATUS       current
    DESCRIPTION
        "Cisco Firepower equipment:PsuCapProvider:promCardType
        managed object property"
    ::= { cfprEquipmentPsuCapProviderEntry 13 }

cfprEquipmentPsuCapProviderRevision OBJECT-TYPE
    SYNTAX       SnmpAdminString
    MAX-ACCESS   read-only
    STATUS       current
    DESCRIPTION
        "Cisco Firepower equipment:PsuCapProvider:revision
        managed object property"
    ::= { cfprEquipmentPsuCapProviderEntry 14 }

cfprEquipmentPsuCapProviderVendor OBJECT-TYPE
    SYNTAX       SnmpAdminString
    MAX-ACCESS   read-only
    STATUS       current
    DESCRIPTION
        "Cisco Firepower equipment:PsuCapProvider:vendor
        managed object property"
    ::= { cfprEquipmentPsuCapProviderEntry 15 }

cfprEquipmentPsuDefTable OBJECT-TYPE
    SYNTAX           SEQUENCE OF CfprEquipmentPsuDefEntry
    MAX-ACCESS       not-accessible
    STATUS           current
    DESCRIPTION
        "Cisco Firepower equipment:PsuDef managed object table"
    ::= { cfprEquipmentObjects 111 }

cfprEquipmentPsuDefEntry OBJECT-TYPE
    SYNTAX           CfprEquipmentPsuDefEntry
    MAX-ACCESS       not-accessible
    STATUS           current
    DESCRIPTION
        "Entry for the cfprEquipmentPsuDefTable table."
    INDEX { cfprEquipmentPsuDefInstanceId }
    ::= { cfprEquipmentPsuDefTable 1 }

CfprEquipmentPsuDefEntry ::= SEQUENCE {
    cfprEquipmentPsuDefInstanceId                                    CfprManagedObjectId,
    cfprEquipmentPsuDefDn                                            CfprManagedObjectDn,
    cfprEquipmentPsuDefRn                                            SnmpAdminString,
    cfprEquipmentPsuDefPsuType                                       SnmpAdminString,
    cfprEquipmentPsuDefDescr                                         SnmpAdminString,
    cfprEquipmentPsuDefIntId                                         SnmpAdminString,
    cfprEquipmentPsuDefName                                          SnmpAdminString,
    cfprEquipmentPsuDefPolicyLevel                                   Gauge32,
    cfprEquipmentPsuDefPolicyOwner                                   CfprPolicyPolicyOwner
}

cfprEquipmentPsuDefInstanceId OBJECT-TYPE
    SYNTAX       CfprManagedObjectId
    MAX-ACCESS   not-accessible
    STATUS       current
    DESCRIPTION
        "Instance identifier of the managed object."
    ::= { cfprEquipmentPsuDefEntry 1 }

cfprEquipmentPsuDefDn OBJECT-TYPE
    SYNTAX       CfprManagedObjectDn
    MAX-ACCESS   read-only
    STATUS       current
    DESCRIPTION
        "Cisco Firepower equipment:PsuDef:dn managed object property"
    ::= { cfprEquipmentPsuDefEntry 2 }

cfprEquipmentPsuDefRn OBJECT-TYPE
    SYNTAX       SnmpAdminString
    MAX-ACCESS   read-only
    STATUS       current
    DESCRIPTION
        "Cisco Firepower equipment:PsuDef:rn managed object property"
    ::= { cfprEquipmentPsuDefEntry 3 }

cfprEquipmentPsuDefPsuType OBJECT-TYPE
    SYNTAX       SnmpAdminString
    MAX-ACCESS   read-only
    STATUS       current
    DESCRIPTION
        "Cisco Firepower equipment:PsuDef:PsuType managed object property"
    ::= { cfprEquipmentPsuDefEntry 4 }

cfprEquipmentPsuDefDescr OBJECT-TYPE
    SYNTAX       SnmpAdminString
    MAX-ACCESS   read-only
    STATUS       current
    DESCRIPTION
        "Cisco Firepower equipment:PsuDef:descr managed object property"
    ::= { cfprEquipmentPsuDefEntry 5 }

cfprEquipmentPsuDefIntId OBJECT-TYPE
    SYNTAX       SnmpAdminString
    MAX-ACCESS   read-only
    STATUS       current
    DESCRIPTION
        "Cisco Firepower equipment:PsuDef:intId managed object property"
    ::= { cfprEquipmentPsuDefEntry 6 }

cfprEquipmentPsuDefName OBJECT-TYPE
    SYNTAX       SnmpAdminString
    MAX-ACCESS   read-only
    STATUS       current
    DESCRIPTION
        "Cisco Firepower equipment:PsuDef:name managed object property"
    ::= { cfprEquipmentPsuDefEntry 7 }

cfprEquipmentPsuDefPolicyLevel OBJECT-TYPE
    SYNTAX       Gauge32
    MAX-ACCESS   read-only
    STATUS       current
    DESCRIPTION
        "Cisco Firepower equipment:PsuDef:policyLevel managed
        object property"
    ::= { cfprEquipmentPsuDefEntry 8 }

cfprEquipmentPsuDefPolicyOwner OBJECT-TYPE
    SYNTAX       CfprPolicyPolicyOwner
    MAX-ACCESS   read-only
    STATUS       current
    DESCRIPTION
        "Cisco Firepower equipment:PsuDef:policyOwner managed
        object property"
    ::= { cfprEquipmentPsuDefEntry 9 }

cfprEquipmentPsuEnvTable OBJECT-TYPE
    SYNTAX           SEQUENCE OF CfprEquipmentPsuEnvEntry
    MAX-ACCESS       not-accessible
    STATUS           current
    DESCRIPTION
        "Cisco Firepower equipment:PsuEnv managed object table"
    ::= { cfprEquipmentObjects 157 }

cfprEquipmentPsuEnvEntry OBJECT-TYPE
    SYNTAX           CfprEquipmentPsuEnvEntry
    MAX-ACCESS       not-accessible
    STATUS           current
    DESCRIPTION
        "Entry for the cfprEquipmentPsuEnvTable table."
    INDEX { cfprEquipmentPsuEnvInstanceId }
    ::= { cfprEquipmentPsuEnvTable 1 }

CfprEquipmentPsuEnvEntry ::= SEQUENCE {
    cfprEquipmentPsuEnvInstanceId                                    CfprManagedObjectId,
    cfprEquipmentPsuEnvDn                                            CfprManagedObjectDn,
    cfprEquipmentPsuEnvRn                                            SnmpAdminString,
    cfprEquipmentPsuEnvId                                            Gauge32,
    cfprEquipmentPsuEnvOperStatus                                    CfprEquipmentOperability,
    cfprEquipmentPsuEnvPsuInput                                      CfprEquipmentSensorThresholdStatus,
    cfprEquipmentPsuEnvPsuOutput                                     CfprEquipmentSensorThresholdStatus,
    cfprEquipmentPsuEnvPsuType                                       CfprEquipmentPsuEnvPsuType
}

cfprEquipmentPsuEnvInstanceId OBJECT-TYPE
    SYNTAX       CfprManagedObjectId
    MAX-ACCESS   not-accessible
    STATUS       current
    DESCRIPTION
        "Instance identifier of the managed object."
    ::= { cfprEquipmentPsuEnvEntry 1 }

cfprEquipmentPsuEnvDn OBJECT-TYPE
    SYNTAX       CfprManagedObjectDn
    MAX-ACCESS   read-only
    STATUS       current
    DESCRIPTION
        "Cisco Firepower equipment:PsuEnv:dn managed object property"
    ::= { cfprEquipmentPsuEnvEntry 2 }

cfprEquipmentPsuEnvRn OBJECT-TYPE
    SYNTAX       SnmpAdminString
    MAX-ACCESS   read-only
    STATUS       current
    DESCRIPTION
        "Cisco Firepower equipment:PsuEnv:rn managed object property"
    ::= { cfprEquipmentPsuEnvEntry 3 }

cfprEquipmentPsuEnvId OBJECT-TYPE
    SYNTAX       Gauge32
    MAX-ACCESS   read-only
    STATUS       current
    DESCRIPTION
        "Cisco Firepower equipment:PsuEnv:id managed object property"
    ::= { cfprEquipmentPsuEnvEntry 4 }

cfprEquipmentPsuEnvOperStatus OBJECT-TYPE
    SYNTAX       CfprEquipmentOperability
    MAX-ACCESS   read-only
    STATUS       current
    DESCRIPTION
        "Cisco Firepower equipment:PsuEnv:operStatus managed
        object property"
    ::= { cfprEquipmentPsuEnvEntry 5 }

cfprEquipmentPsuEnvPsuInput OBJECT-TYPE
    SYNTAX       CfprEquipmentSensorThresholdStatus
    MAX-ACCESS   read-only
    STATUS       current
    DESCRIPTION
        "Cisco Firepower equipment:PsuEnv:psuInput managed
        object property"
    ::= { cfprEquipmentPsuEnvEntry 6 }

cfprEquipmentPsuEnvPsuOutput OBJECT-TYPE
    SYNTAX       CfprEquipmentSensorThresholdStatus
    MAX-ACCESS   read-only
    STATUS       current
    DESCRIPTION
        "Cisco Firepower equipment:PsuEnv:psuOutput managed
        object property"
    ::= { cfprEquipmentPsuEnvEntry 7 }

cfprEquipmentPsuEnvPsuType OBJECT-TYPE
    SYNTAX       CfprEquipmentPsuEnvPsuType
    MAX-ACCESS   read-only
    STATUS       current
    DESCRIPTION
        "Cisco Firepower equipment:PsuEnv:psuType managed object property"
    ::= { cfprEquipmentPsuEnvEntry 8 }

cfprEquipmentPsuInputStatsTable OBJECT-TYPE
    SYNTAX           SEQUENCE OF CfprEquipmentPsuInputStatsEntry
    MAX-ACCESS       not-accessible
    STATUS           current
    DESCRIPTION
        "Cisco Firepower equipment:PsuInputStats managed object table"
    ::= { cfprEquipmentObjects 112 }

cfprEquipmentPsuInputStatsEntry OBJECT-TYPE
    SYNTAX           CfprEquipmentPsuInputStatsEntry
    MAX-ACCESS       not-accessible
    STATUS           current
    DESCRIPTION
        "Entry for the cfprEquipmentPsuInputStatsTable table."
    INDEX { cfprEquipmentPsuInputStatsInstanceId }
    ::= { cfprEquipmentPsuInputStatsTable 1 }

CfprEquipmentPsuInputStatsEntry ::= SEQUENCE {
    cfprEquipmentPsuInputStatsInstanceId                             CfprManagedObjectId,
    cfprEquipmentPsuInputStatsDn                                     CfprManagedObjectDn,
    cfprEquipmentPsuInputStatsRn                                     SnmpAdminString,
    cfprEquipmentPsuInputStatsCurrent                                INTEGER,
    cfprEquipmentPsuInputStatsCurrentAvg                             INTEGER,
    cfprEquipmentPsuInputStatsCurrentMax                             INTEGER,
    cfprEquipmentPsuInputStatsCurrentMin                             INTEGER,
    cfprEquipmentPsuInputStatsInputStatus                            SnmpAdminString,
    cfprEquipmentPsuInputStatsIntervals                              Gauge32,
    cfprEquipmentPsuInputStatsPower                                  INTEGER,
    cfprEquipmentPsuInputStatsPowerAvg                               INTEGER,
    cfprEquipmentPsuInputStatsPowerMax                               INTEGER,
    cfprEquipmentPsuInputStatsPowerMin                               INTEGER,
    cfprEquipmentPsuInputStatsSuspect                                TruthValue,
    cfprEquipmentPsuInputStatsThresholded                            CfprEquipmentPsuInputStatsThresholded,
    cfprEquipmentPsuInputStatsTimeCollected                          DateAndTime,
    cfprEquipmentPsuInputStatsUpdate                                 Gauge32,
    cfprEquipmentPsuInputStatsVoltage                                INTEGER,
    cfprEquipmentPsuInputStatsVoltageAvg                             INTEGER,
    cfprEquipmentPsuInputStatsVoltageMax                             INTEGER,
    cfprEquipmentPsuInputStatsVoltageMin                             INTEGER
}

cfprEquipmentPsuInputStatsInstanceId OBJECT-TYPE
    SYNTAX       CfprManagedObjectId
    MAX-ACCESS   not-accessible
    STATUS       current
    DESCRIPTION
        "Instance identifier of the managed object."
    ::= { cfprEquipmentPsuInputStatsEntry 1 }

cfprEquipmentPsuInputStatsDn OBJECT-TYPE
    SYNTAX       CfprManagedObjectDn
    MAX-ACCESS   read-only
    STATUS       current
    DESCRIPTION
        "Cisco Firepower equipment:PsuInputStats:dn managed
        object property"
    ::= { cfprEquipmentPsuInputStatsEntry 2 }

cfprEquipmentPsuInputStatsRn OBJECT-TYPE
    SYNTAX       SnmpAdminString
    MAX-ACCESS   read-only
    STATUS       current
    DESCRIPTION
        "Cisco Firepower equipment:PsuInputStats:rn managed
        object property"
    ::= { cfprEquipmentPsuInputStatsEntry 3 }

cfprEquipmentPsuInputStatsCurrent OBJECT-TYPE
    SYNTAX       INTEGER
    MAX-ACCESS   read-only
    STATUS       current
    DESCRIPTION
        "Cisco Firepower equipment:PsuInputStats:current
        managed object property"
    ::= { cfprEquipmentPsuInputStatsEntry 4 }

cfprEquipmentPsuInputStatsCurrentAvg OBJECT-TYPE
    SYNTAX       INTEGER
    MAX-ACCESS   read-only
    STATUS       current
    DESCRIPTION
        "Cisco Firepower equipment:PsuInputStats:currentAvg
        managed object property"
    ::= { cfprEquipmentPsuInputStatsEntry 5 }

cfprEquipmentPsuInputStatsCurrentMax OBJECT-TYPE
    SYNTAX       INTEGER
    MAX-ACCESS   read-only
    STATUS       current
    DESCRIPTION
        "Cisco Firepower equipment:PsuInputStats:currentMax
        managed object property"
    ::= { cfprEquipmentPsuInputStatsEntry 6 }

cfprEquipmentPsuInputStatsCurrentMin OBJECT-TYPE
    SYNTAX       INTEGER
    MAX-ACCESS   read-only
    STATUS       current
    DESCRIPTION
        "Cisco Firepower equipment:PsuInputStats:currentMin
        managed object property"
    ::= { cfprEquipmentPsuInputStatsEntry 7 }

cfprEquipmentPsuInputStatsInputStatus OBJECT-TYPE
    SYNTAX       SnmpAdminString
    MAX-ACCESS   read-only
    STATUS       current
    DESCRIPTION
        "Cisco Firepower equipment:PsuInputStats:inputStatus
        managed object property"
    ::= { cfprEquipmentPsuInputStatsEntry 8 }

cfprEquipmentPsuInputStatsIntervals OBJECT-TYPE
    SYNTAX       Gauge32
    MAX-ACCESS   read-only
    STATUS       current
    DESCRIPTION
        "Cisco Firepower equipment:PsuInputStats:intervals
        managed object property"
    ::= { cfprEquipmentPsuInputStatsEntry 9 }

cfprEquipmentPsuInputStatsPower OBJECT-TYPE
    SYNTAX       INTEGER
    MAX-ACCESS   read-only
    STATUS       current
    DESCRIPTION
        "Cisco Firepower equipment:PsuInputStats:power
        managed object property"
    ::= { cfprEquipmentPsuInputStatsEntry 10 }

cfprEquipmentPsuInputStatsPowerAvg OBJECT-TYPE
    SYNTAX       INTEGER
    MAX-ACCESS   read-only
    STATUS       current
    DESCRIPTION
        "Cisco Firepower equipment:PsuInputStats:powerAvg
        managed object property"
    ::= { cfprEquipmentPsuInputStatsEntry 11 }

cfprEquipmentPsuInputStatsPowerMax OBJECT-TYPE
    SYNTAX       INTEGER
    MAX-ACCESS   read-only
    STATUS       current
    DESCRIPTION
        "Cisco Firepower equipment:PsuInputStats:powerMax
        managed object property"
    ::= { cfprEquipmentPsuInputStatsEntry 12 }

cfprEquipmentPsuInputStatsPowerMin OBJECT-TYPE
    SYNTAX       INTEGER
    MAX-ACCESS   read-only
    STATUS       current
    DESCRIPTION
        "Cisco Firepower equipment:PsuInputStats:powerMin
        managed object property"
    ::= { cfprEquipmentPsuInputStatsEntry 13 }

cfprEquipmentPsuInputStatsSuspect OBJECT-TYPE
    SYNTAX       TruthValue
    MAX-ACCESS   read-only
    STATUS       current
    DESCRIPTION
        "Cisco Firepower equipment:PsuInputStats:suspect
        managed object property"
    ::= { cfprEquipmentPsuInputStatsEntry 14 }

cfprEquipmentPsuInputStatsThresholded OBJECT-TYPE
    SYNTAX       CfprEquipmentPsuInputStatsThresholded
    MAX-ACCESS   read-only
    STATUS       current
    DESCRIPTION
        "Cisco Firepower equipment:PsuInputStats:thresholded
        managed object property"
    ::= { cfprEquipmentPsuInputStatsEntry 15 }

cfprEquipmentPsuInputStatsTimeCollected OBJECT-TYPE
    SYNTAX       DateAndTime
    MAX-ACCESS   read-only
    STATUS       current
    DESCRIPTION
        "Cisco Firepower equipment:PsuInputStats:timeCollected
        managed object property"
    ::= { cfprEquipmentPsuInputStatsEntry 16 }

cfprEquipmentPsuInputStatsUpdate OBJECT-TYPE
    SYNTAX       Gauge32
    MAX-ACCESS   read-only
    STATUS       current
    DESCRIPTION
        "Cisco Firepower equipment:PsuInputStats:update
        managed object property"
    ::= { cfprEquipmentPsuInputStatsEntry 17 }

cfprEquipmentPsuInputStatsVoltage OBJECT-TYPE
    SYNTAX       INTEGER
    MAX-ACCESS   read-only
    STATUS       current
    DESCRIPTION
        "Cisco Firepower equipment:PsuInputStats:voltage
        managed object property"
    ::= { cfprEquipmentPsuInputStatsEntry 18 }

cfprEquipmentPsuInputStatsVoltageAvg OBJECT-TYPE
    SYNTAX       INTEGER
    MAX-ACCESS   read-only
    STATUS       current
    DESCRIPTION
        "Cisco Firepower equipment:PsuInputStats:voltageAvg
        managed object property"
    ::= { cfprEquipmentPsuInputStatsEntry 19 }

cfprEquipmentPsuInputStatsVoltageMax OBJECT-TYPE
    SYNTAX       INTEGER
    MAX-ACCESS   read-only
    STATUS       current
    DESCRIPTION
        "Cisco Firepower equipment:PsuInputStats:voltageMax
        managed object property"
    ::= { cfprEquipmentPsuInputStatsEntry 20 }

cfprEquipmentPsuInputStatsVoltageMin OBJECT-TYPE
    SYNTAX       INTEGER
    MAX-ACCESS   read-only
    STATUS       current
    DESCRIPTION
        "Cisco Firepower equipment:PsuInputStats:voltageMin
        managed object property"
    ::= { cfprEquipmentPsuInputStatsEntry 21 }

cfprEquipmentPsuInputStatsHistTable OBJECT-TYPE
    SYNTAX           SEQUENCE OF CfprEquipmentPsuInputStatsHistEntry
    MAX-ACCESS       not-accessible
    STATUS           current
    DESCRIPTION
        "Cisco Firepower equipment:PsuInputStatsHist managed object table"
    ::= { cfprEquipmentObjects 113 }

cfprEquipmentPsuInputStatsHistEntry OBJECT-TYPE
    SYNTAX           CfprEquipmentPsuInputStatsHistEntry
    MAX-ACCESS       not-accessible
    STATUS           current
    DESCRIPTION
        "Entry for the cfprEquipmentPsuInputStatsHistTable table."
    INDEX { cfprEquipmentPsuInputStatsHistInstanceId }
    ::= { cfprEquipmentPsuInputStatsHistTable 1 }

CfprEquipmentPsuInputStatsHistEntry ::= SEQUENCE {
    cfprEquipmentPsuInputStatsHistInstanceId                         CfprManagedObjectId,
    cfprEquipmentPsuInputStatsHistDn                                 CfprManagedObjectDn,
    cfprEquipmentPsuInputStatsHistRn                                 SnmpAdminString,
    cfprEquipmentPsuInputStatsHistCurrent                            INTEGER,
    cfprEquipmentPsuInputStatsHistCurrentAvg                         INTEGER,
    cfprEquipmentPsuInputStatsHistCurrentMax                         INTEGER,
    cfprEquipmentPsuInputStatsHistCurrentMin                         INTEGER,
    cfprEquipmentPsuInputStatsHistId                                 Unsigned64,
    cfprEquipmentPsuInputStatsHistMostRecent                         TruthValue,
    cfprEquipmentPsuInputStatsHistPower                              INTEGER,
    cfprEquipmentPsuInputStatsHistPowerAvg                           INTEGER,
    cfprEquipmentPsuInputStatsHistPowerMax                           INTEGER,
    cfprEquipmentPsuInputStatsHistPowerMin                           INTEGER,
    cfprEquipmentPsuInputStatsHistSuspect                            TruthValue,
    cfprEquipmentPsuInputStatsHistThresholded                        CfprEquipmentPsuInputStatsHistThresholded,
    cfprEquipmentPsuInputStatsHistTimeCollected                      DateAndTime,
    cfprEquipmentPsuInputStatsHistVoltage                            INTEGER,
    cfprEquipmentPsuInputStatsHistVoltageAvg                         INTEGER,
    cfprEquipmentPsuInputStatsHistVoltageMax                         INTEGER,
    cfprEquipmentPsuInputStatsHistVoltageMin                         INTEGER
}

cfprEquipmentPsuInputStatsHistInstanceId OBJECT-TYPE
    SYNTAX       CfprManagedObjectId
    MAX-ACCESS   not-accessible
    STATUS       current
    DESCRIPTION
        "Instance identifier of the managed object."
    ::= { cfprEquipmentPsuInputStatsHistEntry 1 }

cfprEquipmentPsuInputStatsHistDn OBJECT-TYPE
    SYNTAX       CfprManagedObjectDn
    MAX-ACCESS   read-only
    STATUS       current
    DESCRIPTION
        "Cisco Firepower equipment:PsuInputStatsHist:dn
        managed object property"
    ::= { cfprEquipmentPsuInputStatsHistEntry 2 }

cfprEquipmentPsuInputStatsHistRn OBJECT-TYPE
    SYNTAX       SnmpAdminString
    MAX-ACCESS   read-only
    STATUS       current
    DESCRIPTION
        "Cisco Firepower equipment:PsuInputStatsHist:rn
        managed object property"
    ::= { cfprEquipmentPsuInputStatsHistEntry 3 }

cfprEquipmentPsuInputStatsHistCurrent OBJECT-TYPE
    SYNTAX       INTEGER
    MAX-ACCESS   read-only
    STATUS       current
    DESCRIPTION
        "Cisco Firepower equipment:PsuInputStatsHist:current
        managed object property"
    ::= { cfprEquipmentPsuInputStatsHistEntry 4 }

cfprEquipmentPsuInputStatsHistCurrentAvg OBJECT-TYPE
    SYNTAX       INTEGER
    MAX-ACCESS   read-only
    STATUS       current
    DESCRIPTION
        "Cisco Firepower equipment:PsuInputStatsHist:currentAvg
        managed object property"
    ::= { cfprEquipmentPsuInputStatsHistEntry 5 }

cfprEquipmentPsuInputStatsHistCurrentMax OBJECT-TYPE
    SYNTAX       INTEGER
    MAX-ACCESS   read-only
    STATUS       current
    DESCRIPTION
        "Cisco Firepower equipment:PsuInputStatsHist:currentMax
        managed object property"
    ::= { cfprEquipmentPsuInputStatsHistEntry 6 }

cfprEquipmentPsuInputStatsHistCurrentMin OBJECT-TYPE
    SYNTAX       INTEGER
    MAX-ACCESS   read-only
    STATUS       current
    DESCRIPTION
        "Cisco Firepower equipment:PsuInputStatsHist:currentMin
        managed object property"
    ::= { cfprEquipmentPsuInputStatsHistEntry 7 }

cfprEquipmentPsuInputStatsHistId OBJECT-TYPE
    SYNTAX       Unsigned64
    MAX-ACCESS   read-only
    STATUS       current
    DESCRIPTION
        "Cisco Firepower equipment:PsuInputStatsHist:id
        managed object property"
    ::= { cfprEquipmentPsuInputStatsHistEntry 8 }

cfprEquipmentPsuInputStatsHistMostRecent OBJECT-TYPE
    SYNTAX       TruthValue
    MAX-ACCESS   read-only
    STATUS       current
    DESCRIPTION
        "Cisco Firepower equipment:PsuInputStatsHist:mostRecent
        managed object property"
    ::= { cfprEquipmentPsuInputStatsHistEntry 9 }

cfprEquipmentPsuInputStatsHistPower OBJECT-TYPE
    SYNTAX       INTEGER
    MAX-ACCESS   read-only
    STATUS       current
    DESCRIPTION
        "Cisco Firepower equipment:PsuInputStatsHist:power
        managed object property"
    ::= { cfprEquipmentPsuInputStatsHistEntry 10 }

cfprEquipmentPsuInputStatsHistPowerAvg OBJECT-TYPE
    SYNTAX       INTEGER
    MAX-ACCESS   read-only
    STATUS       current
    DESCRIPTION
        "Cisco Firepower equipment:PsuInputStatsHist:powerAvg
        managed object property"
    ::= { cfprEquipmentPsuInputStatsHistEntry 11 }

cfprEquipmentPsuInputStatsHistPowerMax OBJECT-TYPE
    SYNTAX       INTEGER
    MAX-ACCESS   read-only
    STATUS       current
    DESCRIPTION
        "Cisco Firepower equipment:PsuInputStatsHist:powerMax
        managed object property"
    ::= { cfprEquipmentPsuInputStatsHistEntry 12 }

cfprEquipmentPsuInputStatsHistPowerMin OBJECT-TYPE
    SYNTAX       INTEGER
    MAX-ACCESS   read-only
    STATUS       current
    DESCRIPTION
        "Cisco Firepower equipment:PsuInputStatsHist:powerMin
        managed object property"
    ::= { cfprEquipmentPsuInputStatsHistEntry 13 }

cfprEquipmentPsuInputStatsHistSuspect OBJECT-TYPE
    SYNTAX       TruthValue
    MAX-ACCESS   read-only
    STATUS       current
    DESCRIPTION
        "Cisco Firepower equipment:PsuInputStatsHist:suspect
        managed object property"
    ::= { cfprEquipmentPsuInputStatsHistEntry 14 }

cfprEquipmentPsuInputStatsHistThresholded OBJECT-TYPE
    SYNTAX       CfprEquipmentPsuInputStatsHistThresholded
    MAX-ACCESS   read-only
    STATUS       current
    DESCRIPTION
        "Cisco Firepower equipment:PsuInputStatsHist:thresholded
        managed object property"
    ::= { cfprEquipmentPsuInputStatsHistEntry 15 }

cfprEquipmentPsuInputStatsHistTimeCollected OBJECT-TYPE
    SYNTAX       DateAndTime
    MAX-ACCESS   read-only
    STATUS       current
    DESCRIPTION
        "Cisco Firepower equipment:PsuInputStatsHist:timeCollected
        managed object property"
    ::= { cfprEquipmentPsuInputStatsHistEntry 16 }

cfprEquipmentPsuInputStatsHistVoltage OBJECT-TYPE
    SYNTAX       INTEGER
    MAX-ACCESS   read-only
    STATUS       current
    DESCRIPTION
        "Cisco Firepower equipment:PsuInputStatsHist:voltage
        managed object property"
    ::= { cfprEquipmentPsuInputStatsHistEntry 17 }

cfprEquipmentPsuInputStatsHistVoltageAvg OBJECT-TYPE
    SYNTAX       INTEGER
    MAX-ACCESS   read-only
    STATUS       current
    DESCRIPTION
        "Cisco Firepower equipment:PsuInputStatsHist:voltageAvg
        managed object property"
    ::= { cfprEquipmentPsuInputStatsHistEntry 18 }

cfprEquipmentPsuInputStatsHistVoltageMax OBJECT-TYPE
    SYNTAX       INTEGER
    MAX-ACCESS   read-only
    STATUS       current
    DESCRIPTION
        "Cisco Firepower equipment:PsuInputStatsHist:voltageMax
        managed object property"
    ::= { cfprEquipmentPsuInputStatsHistEntry 19 }

cfprEquipmentPsuInputStatsHistVoltageMin OBJECT-TYPE
    SYNTAX       INTEGER
    MAX-ACCESS   read-only
    STATUS       current
    DESCRIPTION
        "Cisco Firepower equipment:PsuInputStatsHist:voltageMin
        managed object property"
    ::= { cfprEquipmentPsuInputStatsHistEntry 20 }

cfprEquipmentPsuOutputStatsTable OBJECT-TYPE
    SYNTAX           SEQUENCE OF CfprEquipmentPsuOutputStatsEntry
    MAX-ACCESS       not-accessible
    STATUS           current
    DESCRIPTION
        "Cisco Firepower equipment:PsuOutputStats managed object table"
    ::= { cfprEquipmentObjects 114 }

cfprEquipmentPsuOutputStatsEntry OBJECT-TYPE
    SYNTAX           CfprEquipmentPsuOutputStatsEntry
    MAX-ACCESS       not-accessible
    STATUS           current
    DESCRIPTION
        "Entry for the cfprEquipmentPsuOutputStatsTable table."
    INDEX { cfprEquipmentPsuOutputStatsInstanceId }
    ::= { cfprEquipmentPsuOutputStatsTable 1 }

CfprEquipmentPsuOutputStatsEntry ::= SEQUENCE {
    cfprEquipmentPsuOutputStatsInstanceId                            CfprManagedObjectId,
    cfprEquipmentPsuOutputStatsDn                                    CfprManagedObjectDn,
    cfprEquipmentPsuOutputStatsRn                                    SnmpAdminString,
    cfprEquipmentPsuOutputStatsCurrent                               INTEGER,
    cfprEquipmentPsuOutputStatsCurrentAvg                            INTEGER,
    cfprEquipmentPsuOutputStatsCurrentMax                            INTEGER,
    cfprEquipmentPsuOutputStatsCurrentMin                            INTEGER,
    cfprEquipmentPsuOutputStatsIntervals                             Gauge32,
    cfprEquipmentPsuOutputStatsOutputStatus                          SnmpAdminString,
    cfprEquipmentPsuOutputStatsPower                                 INTEGER,
    cfprEquipmentPsuOutputStatsPowerAvg                              INTEGER,
    cfprEquipmentPsuOutputStatsPowerMax                              INTEGER,
    cfprEquipmentPsuOutputStatsPowerMin                              INTEGER,
    cfprEquipmentPsuOutputStatsSuspect                               TruthValue,
    cfprEquipmentPsuOutputStatsThresholded                           CfprEquipmentPsuOutputStatsThresholded,
    cfprEquipmentPsuOutputStatsTimeCollected                         DateAndTime,
    cfprEquipmentPsuOutputStatsUpdate                                Gauge32,
    cfprEquipmentPsuOutputStatsVoltage                               INTEGER,
    cfprEquipmentPsuOutputStatsVoltageAvg                            INTEGER,
    cfprEquipmentPsuOutputStatsVoltageMax                            INTEGER,
    cfprEquipmentPsuOutputStatsVoltageMin                            INTEGER
}

cfprEquipmentPsuOutputStatsInstanceId OBJECT-TYPE
    SYNTAX       CfprManagedObjectId
    MAX-ACCESS   not-accessible
    STATUS       current
    DESCRIPTION
        "Instance identifier of the managed object."
    ::= { cfprEquipmentPsuOutputStatsEntry 1 }

cfprEquipmentPsuOutputStatsDn OBJECT-TYPE
    SYNTAX       CfprManagedObjectDn
    MAX-ACCESS   read-only
    STATUS       current
    DESCRIPTION
        "Cisco Firepower equipment:PsuOutputStats:dn managed
        object property"
    ::= { cfprEquipmentPsuOutputStatsEntry 2 }

cfprEquipmentPsuOutputStatsRn OBJECT-TYPE
    SYNTAX       SnmpAdminString
    MAX-ACCESS   read-only
    STATUS       current
    DESCRIPTION
        "Cisco Firepower equipment:PsuOutputStats:rn managed
        object property"
    ::= { cfprEquipmentPsuOutputStatsEntry 3 }

cfprEquipmentPsuOutputStatsCurrent OBJECT-TYPE
    SYNTAX       INTEGER
    MAX-ACCESS   read-only
    STATUS       current
    DESCRIPTION
        "Cisco Firepower equipment:PsuOutputStats:current
        managed object property"
    ::= { cfprEquipmentPsuOutputStatsEntry 4 }

cfprEquipmentPsuOutputStatsCurrentAvg OBJECT-TYPE
    SYNTAX       INTEGER
    MAX-ACCESS   read-only
    STATUS       current
    DESCRIPTION
        "Cisco Firepower equipment:PsuOutputStats:currentAvg
        managed object property"
    ::= { cfprEquipmentPsuOutputStatsEntry 5 }

cfprEquipmentPsuOutputStatsCurrentMax OBJECT-TYPE
    SYNTAX       INTEGER
    MAX-ACCESS   read-only
    STATUS       current
    DESCRIPTION
        "Cisco Firepower equipment:PsuOutputStats:currentMax
        managed object property"
    ::= { cfprEquipmentPsuOutputStatsEntry 6 }

cfprEquipmentPsuOutputStatsCurrentMin OBJECT-TYPE
    SYNTAX       INTEGER
    MAX-ACCESS   read-only
    STATUS       current
    DESCRIPTION
        "Cisco Firepower equipment:PsuOutputStats:currentMin
        managed object property"
    ::= { cfprEquipmentPsuOutputStatsEntry 7 }

cfprEquipmentPsuOutputStatsIntervals OBJECT-TYPE
    SYNTAX       Gauge32
    MAX-ACCESS   read-only
    STATUS       current
    DESCRIPTION
        "Cisco Firepower equipment:PsuOutputStats:intervals
        managed object property"
    ::= { cfprEquipmentPsuOutputStatsEntry 8 }

cfprEquipmentPsuOutputStatsOutputStatus OBJECT-TYPE
    SYNTAX       SnmpAdminString
    MAX-ACCESS   read-only
    STATUS       current
    DESCRIPTION
        "Cisco Firepower equipment:PsuOutputStats:outputStatus
        managed object property"
    ::= { cfprEquipmentPsuOutputStatsEntry 9 }

cfprEquipmentPsuOutputStatsPower OBJECT-TYPE
    SYNTAX       INTEGER
    MAX-ACCESS   read-only
    STATUS       current
    DESCRIPTION
        "Cisco Firepower equipment:PsuOutputStats:power
        managed object property"
    ::= { cfprEquipmentPsuOutputStatsEntry 10 }

cfprEquipmentPsuOutputStatsPowerAvg OBJECT-TYPE
    SYNTAX       INTEGER
    MAX-ACCESS   read-only
    STATUS       current
    DESCRIPTION
        "Cisco Firepower equipment:PsuOutputStats:powerAvg
        managed object property"
    ::= { cfprEquipmentPsuOutputStatsEntry 11 }

cfprEquipmentPsuOutputStatsPowerMax OBJECT-TYPE
    SYNTAX       INTEGER
    MAX-ACCESS   read-only
    STATUS       current
    DESCRIPTION
        "Cisco Firepower equipment:PsuOutputStats:powerMax
        managed object property"
    ::= { cfprEquipmentPsuOutputStatsEntry 12 }

cfprEquipmentPsuOutputStatsPowerMin OBJECT-TYPE
    SYNTAX       INTEGER
    MAX-ACCESS   read-only
    STATUS       current
    DESCRIPTION
        "Cisco Firepower equipment:PsuOutputStats:powerMin
        managed object property"
    ::= { cfprEquipmentPsuOutputStatsEntry 13 }

cfprEquipmentPsuOutputStatsSuspect OBJECT-TYPE
    SYNTAX       TruthValue
    MAX-ACCESS   read-only
    STATUS       current
    DESCRIPTION
        "Cisco Firepower equipment:PsuOutputStats:suspect
        managed object property"
    ::= { cfprEquipmentPsuOutputStatsEntry 14 }

cfprEquipmentPsuOutputStatsThresholded OBJECT-TYPE
    SYNTAX       CfprEquipmentPsuOutputStatsThresholded
    MAX-ACCESS   read-only
    STATUS       current
    DESCRIPTION
        "Cisco Firepower equipment:PsuOutputStats:thresholded
        managed object property"
    ::= { cfprEquipmentPsuOutputStatsEntry 15 }

cfprEquipmentPsuOutputStatsTimeCollected OBJECT-TYPE
    SYNTAX       DateAndTime
    MAX-ACCESS   read-only
    STATUS       current
    DESCRIPTION
        "Cisco Firepower equipment:PsuOutputStats:timeCollected
        managed object property"
    ::= { cfprEquipmentPsuOutputStatsEntry 16 }

cfprEquipmentPsuOutputStatsUpdate OBJECT-TYPE
    SYNTAX       Gauge32
    MAX-ACCESS   read-only
    STATUS       current
    DESCRIPTION
        "Cisco Firepower equipment:PsuOutputStats:update
        managed object property"
    ::= { cfprEquipmentPsuOutputStatsEntry 17 }

cfprEquipmentPsuOutputStatsVoltage OBJECT-TYPE
    SYNTAX       INTEGER
    MAX-ACCESS   read-only
    STATUS       current
    DESCRIPTION
        "Cisco Firepower equipment:PsuOutputStats:voltage
        managed object property"
    ::= { cfprEquipmentPsuOutputStatsEntry 18 }

cfprEquipmentPsuOutputStatsVoltageAvg OBJECT-TYPE
    SYNTAX       INTEGER
    MAX-ACCESS   read-only
    STATUS       current
    DESCRIPTION
        "Cisco Firepower equipment:PsuOutputStats:voltageAvg
        managed object property"
    ::= { cfprEquipmentPsuOutputStatsEntry 19 }

cfprEquipmentPsuOutputStatsVoltageMax OBJECT-TYPE
    SYNTAX       INTEGER
    MAX-ACCESS   read-only
    STATUS       current
    DESCRIPTION
        "Cisco Firepower equipment:PsuOutputStats:voltageMax
        managed object property"
    ::= { cfprEquipmentPsuOutputStatsEntry 20 }

cfprEquipmentPsuOutputStatsVoltageMin OBJECT-TYPE
    SYNTAX       INTEGER
    MAX-ACCESS   read-only
    STATUS       current
    DESCRIPTION
        "Cisco Firepower equipment:PsuOutputStats:voltageMin
        managed object property"
    ::= { cfprEquipmentPsuOutputStatsEntry 21 }

cfprEquipmentPsuOutputStatsHistTable OBJECT-TYPE
    SYNTAX           SEQUENCE OF CfprEquipmentPsuOutputStatsHistEntry
    MAX-ACCESS       not-accessible
    STATUS           current
    DESCRIPTION
        "Cisco Firepower equipment:PsuOutputStatsHist managed
        object table"
    ::= { cfprEquipmentObjects 115 }

cfprEquipmentPsuOutputStatsHistEntry OBJECT-TYPE
    SYNTAX           CfprEquipmentPsuOutputStatsHistEntry
    MAX-ACCESS       not-accessible
    STATUS           current
    DESCRIPTION
        "Entry for the cfprEquipmentPsuOutputStatsHistTable table."
    INDEX { cfprEquipmentPsuOutputStatsHistInstanceId }
    ::= { cfprEquipmentPsuOutputStatsHistTable 1 }

CfprEquipmentPsuOutputStatsHistEntry ::= SEQUENCE {
    cfprEquipmentPsuOutputStatsHistInstanceId                        CfprManagedObjectId,
    cfprEquipmentPsuOutputStatsHistDn                                CfprManagedObjectDn,
    cfprEquipmentPsuOutputStatsHistRn                                SnmpAdminString,
    cfprEquipmentPsuOutputStatsHistCurrent                           INTEGER,
    cfprEquipmentPsuOutputStatsHistCurrentAvg                        INTEGER,
    cfprEquipmentPsuOutputStatsHistCurrentMax                        INTEGER,
    cfprEquipmentPsuOutputStatsHistCurrentMin                        INTEGER,
    cfprEquipmentPsuOutputStatsHistId                                Unsigned64,
    cfprEquipmentPsuOutputStatsHistMostRecent                        TruthValue,
    cfprEquipmentPsuOutputStatsHistPower                             INTEGER,
    cfprEquipmentPsuOutputStatsHistPowerAvg                          INTEGER,
    cfprEquipmentPsuOutputStatsHistPowerMax                          INTEGER,
    cfprEquipmentPsuOutputStatsHistPowerMin                          INTEGER,
    cfprEquipmentPsuOutputStatsHistSuspect                           TruthValue,
    cfprEquipmentPsuOutputStatsHistThresholded                       CfprEquipmentPsuOutputStatsHistThresholded,
    cfprEquipmentPsuOutputStatsHistTimeCollected                     DateAndTime,
    cfprEquipmentPsuOutputStatsHistVoltage                           INTEGER,
    cfprEquipmentPsuOutputStatsHistVoltageAvg                        INTEGER,
    cfprEquipmentPsuOutputStatsHistVoltageMax                        INTEGER,
    cfprEquipmentPsuOutputStatsHistVoltageMin                        INTEGER
}

cfprEquipmentPsuOutputStatsHistInstanceId OBJECT-TYPE
    SYNTAX       CfprManagedObjectId
    MAX-ACCESS   not-accessible
    STATUS       current
    DESCRIPTION
        "Instance identifier of the managed object."
    ::= { cfprEquipmentPsuOutputStatsHistEntry 1 }

cfprEquipmentPsuOutputStatsHistDn OBJECT-TYPE
    SYNTAX       CfprManagedObjectDn
    MAX-ACCESS   read-only
    STATUS       current
    DESCRIPTION
        "Cisco Firepower equipment:PsuOutputStatsHist:dn
        managed object property"
    ::= { cfprEquipmentPsuOutputStatsHistEntry 2 }

cfprEquipmentPsuOutputStatsHistRn OBJECT-TYPE
    SYNTAX       SnmpAdminString
    MAX-ACCESS   read-only
    STATUS       current
    DESCRIPTION
        "Cisco Firepower equipment:PsuOutputStatsHist:rn
        managed object property"
    ::= { cfprEquipmentPsuOutputStatsHistEntry 3 }

cfprEquipmentPsuOutputStatsHistCurrent OBJECT-TYPE
    SYNTAX       INTEGER
    MAX-ACCESS   read-only
    STATUS       current
    DESCRIPTION
        "Cisco Firepower equipment:PsuOutputStatsHist:current
        managed object property"
    ::= { cfprEquipmentPsuOutputStatsHistEntry 4 }

cfprEquipmentPsuOutputStatsHistCurrentAvg OBJECT-TYPE
    SYNTAX       INTEGER
    MAX-ACCESS   read-only
    STATUS       current
    DESCRIPTION
        "Cisco Firepower equipment:PsuOutputStatsHist:currentAvg
        managed object property"
    ::= { cfprEquipmentPsuOutputStatsHistEntry 5 }

cfprEquipmentPsuOutputStatsHistCurrentMax OBJECT-TYPE
    SYNTAX       INTEGER
    MAX-ACCESS   read-only
    STATUS       current
    DESCRIPTION
        "Cisco Firepower equipment:PsuOutputStatsHist:currentMax
        managed object property"
    ::= { cfprEquipmentPsuOutputStatsHistEntry 6 }

cfprEquipmentPsuOutputStatsHistCurrentMin OBJECT-TYPE
    SYNTAX       INTEGER
    MAX-ACCESS   read-only
    STATUS       current
    DESCRIPTION
        "Cisco Firepower equipment:PsuOutputStatsHist:currentMin
        managed object property"
    ::= { cfprEquipmentPsuOutputStatsHistEntry 7 }

cfprEquipmentPsuOutputStatsHistId OBJECT-TYPE
    SYNTAX       Unsigned64
    MAX-ACCESS   read-only
    STATUS       current
    DESCRIPTION
        "Cisco Firepower equipment:PsuOutputStatsHist:id
        managed object property"
    ::= { cfprEquipmentPsuOutputStatsHistEntry 8 }

cfprEquipmentPsuOutputStatsHistMostRecent OBJECT-TYPE
    SYNTAX       TruthValue
    MAX-ACCESS   read-only
    STATUS       current
    DESCRIPTION
        "Cisco Firepower equipment:PsuOutputStatsHist:mostRecent
        managed object property"
    ::= { cfprEquipmentPsuOutputStatsHistEntry 9 }

cfprEquipmentPsuOutputStatsHistPower OBJECT-TYPE
    SYNTAX       INTEGER
    MAX-ACCESS   read-only
    STATUS       current
    DESCRIPTION
        "Cisco Firepower equipment:PsuOutputStatsHist:power
        managed object property"
    ::= { cfprEquipmentPsuOutputStatsHistEntry 10 }

cfprEquipmentPsuOutputStatsHistPowerAvg OBJECT-TYPE
    SYNTAX       INTEGER
    MAX-ACCESS   read-only
    STATUS       current
    DESCRIPTION
        "Cisco Firepower equipment:PsuOutputStatsHist:powerAvg
        managed object property"
    ::= { cfprEquipmentPsuOutputStatsHistEntry 11 }

cfprEquipmentPsuOutputStatsHistPowerMax OBJECT-TYPE
    SYNTAX       INTEGER
    MAX-ACCESS   read-only
    STATUS       current
    DESCRIPTION
        "Cisco Firepower equipment:PsuOutputStatsHist:powerMax
        managed object property"
    ::= { cfprEquipmentPsuOutputStatsHistEntry 12 }

cfprEquipmentPsuOutputStatsHistPowerMin OBJECT-TYPE
    SYNTAX       INTEGER
    MAX-ACCESS   read-only
    STATUS       current
    DESCRIPTION
        "Cisco Firepower equipment:PsuOutputStatsHist:powerMin
        managed object property"
    ::= { cfprEquipmentPsuOutputStatsHistEntry 13 }

cfprEquipmentPsuOutputStatsHistSuspect OBJECT-TYPE
    SYNTAX       TruthValue
    MAX-ACCESS   read-only
    STATUS       current
    DESCRIPTION
        "Cisco Firepower equipment:PsuOutputStatsHist:suspect
        managed object property"
    ::= { cfprEquipmentPsuOutputStatsHistEntry 14 }

cfprEquipmentPsuOutputStatsHistThresholded OBJECT-TYPE
    SYNTAX       CfprEquipmentPsuOutputStatsHistThresholded
    MAX-ACCESS   read-only
    STATUS       current
    DESCRIPTION
        "Cisco Firepower equipment:PsuOutputStatsHist:thresholded
        managed object property"
    ::= { cfprEquipmentPsuOutputStatsHistEntry 15 }

cfprEquipmentPsuOutputStatsHistTimeCollected OBJECT-TYPE
    SYNTAX       DateAndTime
    MAX-ACCESS   read-only
    STATUS       current
    DESCRIPTION
        "Cisco Firepower equipment:PsuOutputStatsHist:timeCollected
        managed object property"
    ::= { cfprEquipmentPsuOutputStatsHistEntry 16 }

cfprEquipmentPsuOutputStatsHistVoltage OBJECT-TYPE
    SYNTAX       INTEGER
    MAX-ACCESS   read-only
    STATUS       current
    DESCRIPTION
        "Cisco Firepower equipment:PsuOutputStatsHist:voltage
        managed object property"
    ::= { cfprEquipmentPsuOutputStatsHistEntry 17 }

cfprEquipmentPsuOutputStatsHistVoltageAvg OBJECT-TYPE
    SYNTAX       INTEGER
    MAX-ACCESS   read-only
    STATUS       current
    DESCRIPTION
        "Cisco Firepower equipment:PsuOutputStatsHist:voltageAvg
        managed object property"
    ::= { cfprEquipmentPsuOutputStatsHistEntry 18 }

cfprEquipmentPsuOutputStatsHistVoltageMax OBJECT-TYPE
    SYNTAX       INTEGER
    MAX-ACCESS   read-only
    STATUS       current
    DESCRIPTION
        "Cisco Firepower equipment:PsuOutputStatsHist:voltageMax
        managed object property"
    ::= { cfprEquipmentPsuOutputStatsHistEntry 19 }

cfprEquipmentPsuOutputStatsHistVoltageMin OBJECT-TYPE
    SYNTAX       INTEGER
    MAX-ACCESS   read-only
    STATUS       current
    DESCRIPTION
        "Cisco Firepower equipment:PsuOutputStatsHist:voltageMin
        managed object property"
    ::= { cfprEquipmentPsuOutputStatsHistEntry 20 }

cfprEquipmentPsuStatsTable OBJECT-TYPE
    SYNTAX           SEQUENCE OF CfprEquipmentPsuStatsEntry
    MAX-ACCESS       not-accessible
    STATUS           current
    DESCRIPTION
        "Cisco Firepower equipment:PsuStats managed object table"
    ::= { cfprEquipmentObjects 116 }

cfprEquipmentPsuStatsEntry OBJECT-TYPE
    SYNTAX           CfprEquipmentPsuStatsEntry
    MAX-ACCESS       not-accessible
    STATUS           current
    DESCRIPTION
        "Entry for the cfprEquipmentPsuStatsTable table."
    INDEX { cfprEquipmentPsuStatsInstanceId }
    ::= { cfprEquipmentPsuStatsTable 1 }

CfprEquipmentPsuStatsEntry ::= SEQUENCE {
    cfprEquipmentPsuStatsInstanceId                                  CfprManagedObjectId,
    cfprEquipmentPsuStatsDn                                          CfprManagedObjectDn,
    cfprEquipmentPsuStatsRn                                          SnmpAdminString,
    cfprEquipmentPsuStatsAmbientTemp                                 INTEGER,
    cfprEquipmentPsuStatsAmbientTempAvg                              INTEGER,
    cfprEquipmentPsuStatsAmbientTempMax                              INTEGER,
    cfprEquipmentPsuStatsAmbientTempMin                              INTEGER,
    cfprEquipmentPsuStatsInput210v                                   INTEGER,
    cfprEquipmentPsuStatsInput210vAvg                                INTEGER,
    cfprEquipmentPsuStatsInput210vMax                                INTEGER,
    cfprEquipmentPsuStatsInput210vMin                                INTEGER,
    cfprEquipmentPsuStatsIntervals                                   Gauge32,
    cfprEquipmentPsuStatsOutput12v                                   INTEGER,
    cfprEquipmentPsuStatsOutput12vAvg                                INTEGER,
    cfprEquipmentPsuStatsOutput12vMax                                INTEGER,
    cfprEquipmentPsuStatsOutput12vMin                                INTEGER,
    cfprEquipmentPsuStatsOutput3v3                                   INTEGER,
    cfprEquipmentPsuStatsOutput3v3Avg                                INTEGER,
    cfprEquipmentPsuStatsOutput3v3Max                                INTEGER,
    cfprEquipmentPsuStatsOutput3v3Min                                INTEGER,
    cfprEquipmentPsuStatsOutputCurrent                               INTEGER,
    cfprEquipmentPsuStatsOutputCurrentAvg                            INTEGER,
    cfprEquipmentPsuStatsOutputCurrentMax                            INTEGER,
    cfprEquipmentPsuStatsOutputCurrentMin                            INTEGER,
    cfprEquipmentPsuStatsOutputPower                                 INTEGER,
    cfprEquipmentPsuStatsOutputPowerAvg                              INTEGER,
    cfprEquipmentPsuStatsOutputPowerMax                              INTEGER,
    cfprEquipmentPsuStatsOutputPowerMin                              INTEGER,
    cfprEquipmentPsuStatsPsuTemp1                                    INTEGER,
    cfprEquipmentPsuStatsPsuTemp2                                    INTEGER,
    cfprEquipmentPsuStatsSuspect                                     TruthValue,
    cfprEquipmentPsuStatsThresholded                                 CfprEquipmentPsuStatsThresholded,
    cfprEquipmentPsuStatsTimeCollected                               DateAndTime,
    cfprEquipmentPsuStatsUpdate                                      Gauge32
}

cfprEquipmentPsuStatsInstanceId OBJECT-TYPE
    SYNTAX       CfprManagedObjectId
    MAX-ACCESS   not-accessible
    STATUS       current
    DESCRIPTION
        "Instance identifier of the managed object."
    ::= { cfprEquipmentPsuStatsEntry 1 }

cfprEquipmentPsuStatsDn OBJECT-TYPE
    SYNTAX       CfprManagedObjectDn
    MAX-ACCESS   read-only
    STATUS       current
    DESCRIPTION
        "Cisco Firepower equipment:PsuStats:dn managed object property"
    ::= { cfprEquipmentPsuStatsEntry 2 }

cfprEquipmentPsuStatsRn OBJECT-TYPE
    SYNTAX       SnmpAdminString
    MAX-ACCESS   read-only
    STATUS       current
    DESCRIPTION
        "Cisco Firepower equipment:PsuStats:rn managed object property"
    ::= { cfprEquipmentPsuStatsEntry 3 }

cfprEquipmentPsuStatsAmbientTemp OBJECT-TYPE
    SYNTAX       INTEGER
    MAX-ACCESS   read-only
    STATUS       current
    DESCRIPTION
        "Cisco Firepower equipment:PsuStats:ambientTemp
        managed object property"
    ::= { cfprEquipmentPsuStatsEntry 4 }

cfprEquipmentPsuStatsAmbientTempAvg OBJECT-TYPE
    SYNTAX       INTEGER
    MAX-ACCESS   read-only
    STATUS       current
    DESCRIPTION
        "Cisco Firepower equipment:PsuStats:ambientTempAvg
        managed object property"
    ::= { cfprEquipmentPsuStatsEntry 5 }

cfprEquipmentPsuStatsAmbientTempMax OBJECT-TYPE
    SYNTAX       INTEGER
    MAX-ACCESS   read-only
    STATUS       current
    DESCRIPTION
        "Cisco Firepower equipment:PsuStats:ambientTempMax
        managed object property"
    ::= { cfprEquipmentPsuStatsEntry 6 }

cfprEquipmentPsuStatsAmbientTempMin OBJECT-TYPE
    SYNTAX       INTEGER
    MAX-ACCESS   read-only
    STATUS       current
    DESCRIPTION
        "Cisco Firepower equipment:PsuStats:ambientTempMin
        managed object property"
    ::= { cfprEquipmentPsuStatsEntry 7 }

cfprEquipmentPsuStatsInput210v OBJECT-TYPE
    SYNTAX       INTEGER
    MAX-ACCESS   read-only
    STATUS       current
    DESCRIPTION
        "Cisco Firepower equipment:PsuStats:input210v managed
        object property"
    ::= { cfprEquipmentPsuStatsEntry 8 }

cfprEquipmentPsuStatsInput210vAvg OBJECT-TYPE
    SYNTAX       INTEGER
    MAX-ACCESS   read-only
    STATUS       current
    DESCRIPTION
        "Cisco Firepower equipment:PsuStats:input210vAvg
        managed object property"
    ::= { cfprEquipmentPsuStatsEntry 9 }

cfprEquipmentPsuStatsInput210vMax OBJECT-TYPE
    SYNTAX       INTEGER
    MAX-ACCESS   read-only
    STATUS       current
    DESCRIPTION
        "Cisco Firepower equipment:PsuStats:input210vMax
        managed object property"
    ::= { cfprEquipmentPsuStatsEntry 10 }

cfprEquipmentPsuStatsInput210vMin OBJECT-TYPE
    SYNTAX       INTEGER
    MAX-ACCESS   read-only
    STATUS       current
    DESCRIPTION
        "Cisco Firepower equipment:PsuStats:input210vMin
        managed object property"
    ::= { cfprEquipmentPsuStatsEntry 11 }

cfprEquipmentPsuStatsIntervals OBJECT-TYPE
    SYNTAX       Gauge32
    MAX-ACCESS   read-only
    STATUS       current
    DESCRIPTION
        "Cisco Firepower equipment:PsuStats:intervals managed
        object property"
    ::= { cfprEquipmentPsuStatsEntry 12 }

cfprEquipmentPsuStatsOutput12v OBJECT-TYPE
    SYNTAX       INTEGER
    MAX-ACCESS   read-only
    STATUS       current
    DESCRIPTION
        "Cisco Firepower equipment:PsuStats:output12v managed
        object property"
    ::= { cfprEquipmentPsuStatsEntry 13 }

cfprEquipmentPsuStatsOutput12vAvg OBJECT-TYPE
    SYNTAX       INTEGER
    MAX-ACCESS   read-only
    STATUS       current
    DESCRIPTION
        "Cisco Firepower equipment:PsuStats:output12vAvg
        managed object property"
    ::= { cfprEquipmentPsuStatsEntry 14 }

cfprEquipmentPsuStatsOutput12vMax OBJECT-TYPE
    SYNTAX       INTEGER
    MAX-ACCESS   read-only
    STATUS       current
    DESCRIPTION
        "Cisco Firepower equipment:PsuStats:output12vMax
        managed object property"
    ::= { cfprEquipmentPsuStatsEntry 15 }

cfprEquipmentPsuStatsOutput12vMin OBJECT-TYPE
    SYNTAX       INTEGER
    MAX-ACCESS   read-only
    STATUS       current
    DESCRIPTION
        "Cisco Firepower equipment:PsuStats:output12vMin
        managed object property"
    ::= { cfprEquipmentPsuStatsEntry 16 }

cfprEquipmentPsuStatsOutput3v3 OBJECT-TYPE
    SYNTAX       INTEGER
    MAX-ACCESS   read-only
    STATUS       current
    DESCRIPTION
        "Cisco Firepower equipment:PsuStats:output3v3 managed
        object property"
    ::= { cfprEquipmentPsuStatsEntry 17 }

cfprEquipmentPsuStatsOutput3v3Avg OBJECT-TYPE
    SYNTAX       INTEGER
    MAX-ACCESS   read-only
    STATUS       current
    DESCRIPTION
        "Cisco Firepower equipment:PsuStats:output3v3Avg
        managed object property"
    ::= { cfprEquipmentPsuStatsEntry 18 }

cfprEquipmentPsuStatsOutput3v3Max OBJECT-TYPE
    SYNTAX       INTEGER
    MAX-ACCESS   read-only
    STATUS       current
    DESCRIPTION
        "Cisco Firepower equipment:PsuStats:output3v3Max
        managed object property"
    ::= { cfprEquipmentPsuStatsEntry 19 }

cfprEquipmentPsuStatsOutput3v3Min OBJECT-TYPE
    SYNTAX       INTEGER
    MAX-ACCESS   read-only
    STATUS       current
    DESCRIPTION
        "Cisco Firepower equipment:PsuStats:output3v3Min
        managed object property"
    ::= { cfprEquipmentPsuStatsEntry 20 }

cfprEquipmentPsuStatsOutputCurrent OBJECT-TYPE
    SYNTAX       INTEGER
    MAX-ACCESS   read-only
    STATUS       current
    DESCRIPTION
        "Cisco Firepower equipment:PsuStats:outputCurrent
        managed object property"
    ::= { cfprEquipmentPsuStatsEntry 21 }

cfprEquipmentPsuStatsOutputCurrentAvg OBJECT-TYPE
    SYNTAX       INTEGER
    MAX-ACCESS   read-only
    STATUS       current
    DESCRIPTION
        "Cisco Firepower equipment:PsuStats:outputCurrentAvg
        managed object property"
    ::= { cfprEquipmentPsuStatsEntry 22 }

cfprEquipmentPsuStatsOutputCurrentMax OBJECT-TYPE
    SYNTAX       INTEGER
    MAX-ACCESS   read-only
    STATUS       current
    DESCRIPTION
        "Cisco Firepower equipment:PsuStats:outputCurrentMax
        managed object property"
    ::= { cfprEquipmentPsuStatsEntry 23 }

cfprEquipmentPsuStatsOutputCurrentMin OBJECT-TYPE
    SYNTAX       INTEGER
    MAX-ACCESS   read-only
    STATUS       current
    DESCRIPTION
        "Cisco Firepower equipment:PsuStats:outputCurrentMin
        managed object property"
    ::= { cfprEquipmentPsuStatsEntry 24 }

cfprEquipmentPsuStatsOutputPower OBJECT-TYPE
    SYNTAX       INTEGER
    MAX-ACCESS   read-only
    STATUS       current
    DESCRIPTION
        "Cisco Firepower equipment:PsuStats:outputPower
        managed object property"
    ::= { cfprEquipmentPsuStatsEntry 25 }

cfprEquipmentPsuStatsOutputPowerAvg OBJECT-TYPE
    SYNTAX       INTEGER
    MAX-ACCESS   read-only
    STATUS       current
    DESCRIPTION
        "Cisco Firepower equipment:PsuStats:outputPowerAvg
        managed object property"
    ::= { cfprEquipmentPsuStatsEntry 26 }

cfprEquipmentPsuStatsOutputPowerMax OBJECT-TYPE
    SYNTAX       INTEGER
    MAX-ACCESS   read-only
    STATUS       current
    DESCRIPTION
        "Cisco Firepower equipment:PsuStats:outputPowerMax
        managed object property"
    ::= { cfprEquipmentPsuStatsEntry 27 }

cfprEquipmentPsuStatsOutputPowerMin OBJECT-TYPE
    SYNTAX       INTEGER
    MAX-ACCESS   read-only
    STATUS       current
    DESCRIPTION
        "Cisco Firepower equipment:PsuStats:outputPowerMin
        managed object property"
    ::= { cfprEquipmentPsuStatsEntry 28 }

cfprEquipmentPsuStatsPsuTemp1 OBJECT-TYPE
    SYNTAX       INTEGER
    MAX-ACCESS   read-only
    STATUS       current
    DESCRIPTION
        "Cisco Firepower equipment:PsuStats:psuTemp1 managed
        object property"
    ::= { cfprEquipmentPsuStatsEntry 29 }

cfprEquipmentPsuStatsPsuTemp2 OBJECT-TYPE
    SYNTAX       INTEGER
    MAX-ACCESS   read-only
    STATUS       current
    DESCRIPTION
        "Cisco Firepower equipment:PsuStats:psuTemp2 managed
        object property"
    ::= { cfprEquipmentPsuStatsEntry 30 }

cfprEquipmentPsuStatsSuspect OBJECT-TYPE
    SYNTAX       TruthValue
    MAX-ACCESS   read-only
    STATUS       current
    DESCRIPTION
        "Cisco Firepower equipment:PsuStats:suspect managed
        object property"
    ::= { cfprEquipmentPsuStatsEntry 31 }

cfprEquipmentPsuStatsThresholded OBJECT-TYPE
    SYNTAX       CfprEquipmentPsuStatsThresholded
    MAX-ACCESS   read-only
    STATUS       current
    DESCRIPTION
        "Cisco Firepower equipment:PsuStats:thresholded
        managed object property"
    ::= { cfprEquipmentPsuStatsEntry 32 }

cfprEquipmentPsuStatsTimeCollected OBJECT-TYPE
    SYNTAX       DateAndTime
    MAX-ACCESS   read-only
    STATUS       current
    DESCRIPTION
        "Cisco Firepower equipment:PsuStats:timeCollected
        managed object property"
    ::= { cfprEquipmentPsuStatsEntry 33 }

cfprEquipmentPsuStatsUpdate OBJECT-TYPE
    SYNTAX       Gauge32
    MAX-ACCESS   read-only
    STATUS       current
    DESCRIPTION
        "Cisco Firepower equipment:PsuStats:update managed
        object property"
    ::= { cfprEquipmentPsuStatsEntry 34 }

cfprEquipmentPsuStatsHistTable OBJECT-TYPE
    SYNTAX           SEQUENCE OF CfprEquipmentPsuStatsHistEntry
    MAX-ACCESS       not-accessible
    STATUS           current
    DESCRIPTION
        "Cisco Firepower equipment:PsuStatsHist managed object table"
    ::= { cfprEquipmentObjects 117 }

cfprEquipmentPsuStatsHistEntry OBJECT-TYPE
    SYNTAX           CfprEquipmentPsuStatsHistEntry
    MAX-ACCESS       not-accessible
    STATUS           current
    DESCRIPTION
        "Entry for the cfprEquipmentPsuStatsHistTable table."
    INDEX { cfprEquipmentPsuStatsHistInstanceId }
    ::= { cfprEquipmentPsuStatsHistTable 1 }

CfprEquipmentPsuStatsHistEntry ::= SEQUENCE {
    cfprEquipmentPsuStatsHistInstanceId                              CfprManagedObjectId,
    cfprEquipmentPsuStatsHistDn                                      CfprManagedObjectDn,
    cfprEquipmentPsuStatsHistRn                                      SnmpAdminString,
    cfprEquipmentPsuStatsHistAmbientTemp                             INTEGER,
    cfprEquipmentPsuStatsHistAmbientTempAvg                          INTEGER,
    cfprEquipmentPsuStatsHistAmbientTempMax                          INTEGER,
    cfprEquipmentPsuStatsHistAmbientTempMin                          INTEGER,
    cfprEquipmentPsuStatsHistId                                      Unsigned64,
    cfprEquipmentPsuStatsHistInput210v                               INTEGER,
    cfprEquipmentPsuStatsHistInput210vAvg                            INTEGER,
    cfprEquipmentPsuStatsHistInput210vMax                            INTEGER,
    cfprEquipmentPsuStatsHistInput210vMin                            INTEGER,
    cfprEquipmentPsuStatsHistMostRecent                              TruthValue,
    cfprEquipmentPsuStatsHistOutput12v                               INTEGER,
    cfprEquipmentPsuStatsHistOutput12vAvg                            INTEGER,
    cfprEquipmentPsuStatsHistOutput12vMax                            INTEGER,
    cfprEquipmentPsuStatsHistOutput12vMin                            INTEGER,
    cfprEquipmentPsuStatsHistOutput3v3                               INTEGER,
    cfprEquipmentPsuStatsHistOutput3v3Avg                            INTEGER,
    cfprEquipmentPsuStatsHistOutput3v3Max                            INTEGER,
    cfprEquipmentPsuStatsHistOutput3v3Min                            INTEGER,
    cfprEquipmentPsuStatsHistOutputCurrent                           INTEGER,
    cfprEquipmentPsuStatsHistOutputCurrentAvg                        INTEGER,
    cfprEquipmentPsuStatsHistOutputCurrentMax                        INTEGER,
    cfprEquipmentPsuStatsHistOutputCurrentMin                        INTEGER,
    cfprEquipmentPsuStatsHistOutputPower                             INTEGER,
    cfprEquipmentPsuStatsHistOutputPowerAvg                          INTEGER,
    cfprEquipmentPsuStatsHistOutputPowerMax                          INTEGER,
    cfprEquipmentPsuStatsHistOutputPowerMin                          INTEGER,
    cfprEquipmentPsuStatsHistSuspect                                 TruthValue,
    cfprEquipmentPsuStatsHistThresholded                             CfprEquipmentPsuStatsHistThresholded,
    cfprEquipmentPsuStatsHistTimeCollected                           DateAndTime
}

cfprEquipmentPsuStatsHistInstanceId OBJECT-TYPE
    SYNTAX       CfprManagedObjectId
    MAX-ACCESS   not-accessible
    STATUS       current
    DESCRIPTION
        "Instance identifier of the managed object."
    ::= { cfprEquipmentPsuStatsHistEntry 1 }

cfprEquipmentPsuStatsHistDn OBJECT-TYPE
    SYNTAX       CfprManagedObjectDn
    MAX-ACCESS   read-only
    STATUS       current
    DESCRIPTION
        "Cisco Firepower equipment:PsuStatsHist:dn managed
        object property"
    ::= { cfprEquipmentPsuStatsHistEntry 2 }

cfprEquipmentPsuStatsHistRn OBJECT-TYPE
    SYNTAX       SnmpAdminString
    MAX-ACCESS   read-only
    STATUS       current
    DESCRIPTION
        "Cisco Firepower equipment:PsuStatsHist:rn managed
        object property"
    ::= { cfprEquipmentPsuStatsHistEntry 3 }

cfprEquipmentPsuStatsHistAmbientTemp OBJECT-TYPE
    SYNTAX       INTEGER
    MAX-ACCESS   read-only
    STATUS       current
    DESCRIPTION
        "Cisco Firepower equipment:PsuStatsHist:ambientTemp
        managed object property"
    ::= { cfprEquipmentPsuStatsHistEntry 4 }

cfprEquipmentPsuStatsHistAmbientTempAvg OBJECT-TYPE
    SYNTAX       INTEGER
    MAX-ACCESS   read-only
    STATUS       current
    DESCRIPTION
        "Cisco Firepower equipment:PsuStatsHist:ambientTempAvg
        managed object property"
    ::= { cfprEquipmentPsuStatsHistEntry 5 }

cfprEquipmentPsuStatsHistAmbientTempMax OBJECT-TYPE
    SYNTAX       INTEGER
    MAX-ACCESS   read-only
    STATUS       current
    DESCRIPTION
        "Cisco Firepower equipment:PsuStatsHist:ambientTempMax
        managed object property"
    ::= { cfprEquipmentPsuStatsHistEntry 6 }

cfprEquipmentPsuStatsHistAmbientTempMin OBJECT-TYPE
    SYNTAX       INTEGER
    MAX-ACCESS   read-only
    STATUS       current
    DESCRIPTION
        "Cisco Firepower equipment:PsuStatsHist:ambientTempMin
        managed object property"
    ::= { cfprEquipmentPsuStatsHistEntry 7 }

cfprEquipmentPsuStatsHistId OBJECT-TYPE
    SYNTAX       Unsigned64
    MAX-ACCESS   read-only
    STATUS       current
    DESCRIPTION
        "Cisco Firepower equipment:PsuStatsHist:id managed
        object property"
    ::= { cfprEquipmentPsuStatsHistEntry 8 }

cfprEquipmentPsuStatsHistInput210v OBJECT-TYPE
    SYNTAX       INTEGER
    MAX-ACCESS   read-only
    STATUS       current
    DESCRIPTION
        "Cisco Firepower equipment:PsuStatsHist:input210v
        managed object property"
    ::= { cfprEquipmentPsuStatsHistEntry 9 }

cfprEquipmentPsuStatsHistInput210vAvg OBJECT-TYPE
    SYNTAX       INTEGER
    MAX-ACCESS   read-only
    STATUS       current
    DESCRIPTION
        "Cisco Firepower equipment:PsuStatsHist:input210vAvg
        managed object property"
    ::= { cfprEquipmentPsuStatsHistEntry 10 }

cfprEquipmentPsuStatsHistInput210vMax OBJECT-TYPE
    SYNTAX       INTEGER
    MAX-ACCESS   read-only
    STATUS       current
    DESCRIPTION
        "Cisco Firepower equipment:PsuStatsHist:input210vMax
        managed object property"
    ::= { cfprEquipmentPsuStatsHistEntry 11 }

cfprEquipmentPsuStatsHistInput210vMin OBJECT-TYPE
    SYNTAX       INTEGER
    MAX-ACCESS   read-only
    STATUS       current
    DESCRIPTION
        "Cisco Firepower equipment:PsuStatsHist:input210vMin
        managed object property"
    ::= { cfprEquipmentPsuStatsHistEntry 12 }

cfprEquipmentPsuStatsHistMostRecent OBJECT-TYPE
    SYNTAX       TruthValue
    MAX-ACCESS   read-only
    STATUS       current
    DESCRIPTION
        "Cisco Firepower equipment:PsuStatsHist:mostRecent
        managed object property"
    ::= { cfprEquipmentPsuStatsHistEntry 13 }

cfprEquipmentPsuStatsHistOutput12v OBJECT-TYPE
    SYNTAX       INTEGER
    MAX-ACCESS   read-only
    STATUS       current
    DESCRIPTION
        "Cisco Firepower equipment:PsuStatsHist:output12v
        managed object property"
    ::= { cfprEquipmentPsuStatsHistEntry 14 }

cfprEquipmentPsuStatsHistOutput12vAvg OBJECT-TYPE
    SYNTAX       INTEGER
    MAX-ACCESS   read-only
    STATUS       current
    DESCRIPTION
        "Cisco Firepower equipment:PsuStatsHist:output12vAvg
        managed object property"
    ::= { cfprEquipmentPsuStatsHistEntry 15 }

cfprEquipmentPsuStatsHistOutput12vMax OBJECT-TYPE
    SYNTAX       INTEGER
    MAX-ACCESS   read-only
    STATUS       current
    DESCRIPTION
        "Cisco Firepower equipment:PsuStatsHist:output12vMax
        managed object property"
    ::= { cfprEquipmentPsuStatsHistEntry 16 }

cfprEquipmentPsuStatsHistOutput12vMin OBJECT-TYPE
    SYNTAX       INTEGER
    MAX-ACCESS   read-only
    STATUS       current
    DESCRIPTION
        "Cisco Firepower equipment:PsuStatsHist:output12vMin
        managed object property"
    ::= { cfprEquipmentPsuStatsHistEntry 17 }

cfprEquipmentPsuStatsHistOutput3v3 OBJECT-TYPE
    SYNTAX       INTEGER
    MAX-ACCESS   read-only
    STATUS       current
    DESCRIPTION
        "Cisco Firepower equipment:PsuStatsHist:output3v3
        managed object property"
    ::= { cfprEquipmentPsuStatsHistEntry 18 }

cfprEquipmentPsuStatsHistOutput3v3Avg OBJECT-TYPE
    SYNTAX       INTEGER
    MAX-ACCESS   read-only
    STATUS       current
    DESCRIPTION
        "Cisco Firepower equipment:PsuStatsHist:output3v3Avg
        managed object property"
    ::= { cfprEquipmentPsuStatsHistEntry 19 }

cfprEquipmentPsuStatsHistOutput3v3Max OBJECT-TYPE
    SYNTAX       INTEGER
    MAX-ACCESS   read-only
    STATUS       current
    DESCRIPTION
        "Cisco Firepower equipment:PsuStatsHist:output3v3Max
        managed object property"
    ::= { cfprEquipmentPsuStatsHistEntry 20 }

cfprEquipmentPsuStatsHistOutput3v3Min OBJECT-TYPE
    SYNTAX       INTEGER
    MAX-ACCESS   read-only
    STATUS       current
    DESCRIPTION
        "Cisco Firepower equipment:PsuStatsHist:output3v3Min
        managed object property"
    ::= { cfprEquipmentPsuStatsHistEntry 21 }

cfprEquipmentPsuStatsHistOutputCurrent OBJECT-TYPE
    SYNTAX       INTEGER
    MAX-ACCESS   read-only
    STATUS       current
    DESCRIPTION
        "Cisco Firepower equipment:PsuStatsHist:outputCurrent
        managed object property"
    ::= { cfprEquipmentPsuStatsHistEntry 22 }

cfprEquipmentPsuStatsHistOutputCurrentAvg OBJECT-TYPE
    SYNTAX       INTEGER
    MAX-ACCESS   read-only
    STATUS       current
    DESCRIPTION
        "Cisco Firepower equipment:PsuStatsHist:outputCurrentAvg
        managed object property"
    ::= { cfprEquipmentPsuStatsHistEntry 23 }

cfprEquipmentPsuStatsHistOutputCurrentMax OBJECT-TYPE
    SYNTAX       INTEGER
    MAX-ACCESS   read-only
    STATUS       current
    DESCRIPTION
        "Cisco Firepower equipment:PsuStatsHist:outputCurrentMax
        managed object property"
    ::= { cfprEquipmentPsuStatsHistEntry 24 }

cfprEquipmentPsuStatsHistOutputCurrentMin OBJECT-TYPE
    SYNTAX       INTEGER
    MAX-ACCESS   read-only
    STATUS       current
    DESCRIPTION
        "Cisco Firepower equipment:PsuStatsHist:outputCurrentMin
        managed object property"
    ::= { cfprEquipmentPsuStatsHistEntry 25 }

cfprEquipmentPsuStatsHistOutputPower OBJECT-TYPE
    SYNTAX       INTEGER
    MAX-ACCESS   read-only
    STATUS       current
    DESCRIPTION
        "Cisco Firepower equipment:PsuStatsHist:outputPower
        managed object property"
    ::= { cfprEquipmentPsuStatsHistEntry 26 }

cfprEquipmentPsuStatsHistOutputPowerAvg OBJECT-TYPE
    SYNTAX       INTEGER
    MAX-ACCESS   read-only
    STATUS       current
    DESCRIPTION
        "Cisco Firepower equipment:PsuStatsHist:outputPowerAvg
        managed object property"
    ::= { cfprEquipmentPsuStatsHistEntry 27 }

cfprEquipmentPsuStatsHistOutputPowerMax OBJECT-TYPE
    SYNTAX       INTEGER
    MAX-ACCESS   read-only
    STATUS       current
    DESCRIPTION
        "Cisco Firepower equipment:PsuStatsHist:outputPowerMax
        managed object property"
    ::= { cfprEquipmentPsuStatsHistEntry 28 }

cfprEquipmentPsuStatsHistOutputPowerMin OBJECT-TYPE
    SYNTAX       INTEGER
    MAX-ACCESS   read-only
    STATUS       current
    DESCRIPTION
        "Cisco Firepower equipment:PsuStatsHist:outputPowerMin
        managed object property"
    ::= { cfprEquipmentPsuStatsHistEntry 29 }

cfprEquipmentPsuStatsHistSuspect OBJECT-TYPE
    SYNTAX       TruthValue
    MAX-ACCESS   read-only
    STATUS       current
    DESCRIPTION
        "Cisco Firepower equipment:PsuStatsHist:suspect
        managed object property"
    ::= { cfprEquipmentPsuStatsHistEntry 30 }

cfprEquipmentPsuStatsHistThresholded OBJECT-TYPE
    SYNTAX       CfprEquipmentPsuStatsHistThresholded
    MAX-ACCESS   read-only
    STATUS       current
    DESCRIPTION
        "Cisco Firepower equipment:PsuStatsHist:thresholded
        managed object property"
    ::= { cfprEquipmentPsuStatsHistEntry 31 }

cfprEquipmentPsuStatsHistTimeCollected OBJECT-TYPE
    SYNTAX       DateAndTime
    MAX-ACCESS   read-only
    STATUS       current
    DESCRIPTION
        "Cisco Firepower equipment:PsuStatsHist:timeCollected
        managed object property"
    ::= { cfprEquipmentPsuStatsHistEntry 32 }

cfprEquipmentRackFanModuleDefTable OBJECT-TYPE
    SYNTAX           SEQUENCE OF CfprEquipmentRackFanModuleDefEntry
    MAX-ACCESS       not-accessible
    STATUS           current
    DESCRIPTION
        "Cisco Firepower equipment:RackFanModuleDef managed object table"
    ::= { cfprEquipmentObjects 118 }

cfprEquipmentRackFanModuleDefEntry OBJECT-TYPE
    SYNTAX           CfprEquipmentRackFanModuleDefEntry
    MAX-ACCESS       not-accessible
    STATUS           current
    DESCRIPTION
        "Entry for the cfprEquipmentRackFanModuleDefTable table."
    INDEX { cfprEquipmentRackFanModuleDefInstanceId }
    ::= { cfprEquipmentRackFanModuleDefTable 1 }

CfprEquipmentRackFanModuleDefEntry ::= SEQUENCE {
    cfprEquipmentRackFanModuleDefInstanceId                          CfprManagedObjectId,
    cfprEquipmentRackFanModuleDefDn                                  CfprManagedObjectDn,
    cfprEquipmentRackFanModuleDefRn                                  SnmpAdminString,
    cfprEquipmentRackFanModuleDefDescr                               SnmpAdminString,
    cfprEquipmentRackFanModuleDefFanCapacity                         Gauge32,
    cfprEquipmentRackFanModuleDefIntId                               SnmpAdminString,
    cfprEquipmentRackFanModuleDefName                                SnmpAdminString,
    cfprEquipmentRackFanModuleDefPolicyLevel                         Gauge32,
    cfprEquipmentRackFanModuleDefPolicyOwner                         CfprPolicyPolicyOwner
}

cfprEquipmentRackFanModuleDefInstanceId OBJECT-TYPE
    SYNTAX       CfprManagedObjectId
    MAX-ACCESS   not-accessible
    STATUS       current
    DESCRIPTION
        "Instance identifier of the managed object."
    ::= { cfprEquipmentRackFanModuleDefEntry 1 }

cfprEquipmentRackFanModuleDefDn OBJECT-TYPE
    SYNTAX       CfprManagedObjectDn
    MAX-ACCESS   read-only
    STATUS       current
    DESCRIPTION
        "Cisco Firepower equipment:RackFanModuleDef:dn
        managed object property"
    ::= { cfprEquipmentRackFanModuleDefEntry 2 }

cfprEquipmentRackFanModuleDefRn OBJECT-TYPE
    SYNTAX       SnmpAdminString
    MAX-ACCESS   read-only
    STATUS       current
    DESCRIPTION
        "Cisco Firepower equipment:RackFanModuleDef:rn
        managed object property"
    ::= { cfprEquipmentRackFanModuleDefEntry 3 }

cfprEquipmentRackFanModuleDefDescr OBJECT-TYPE
    SYNTAX       SnmpAdminString
    MAX-ACCESS   read-only
    STATUS       current
    DESCRIPTION
        "Cisco Firepower equipment:RackFanModuleDef:descr
        managed object property"
    ::= { cfprEquipmentRackFanModuleDefEntry 4 }

cfprEquipmentRackFanModuleDefFanCapacity OBJECT-TYPE
    SYNTAX       Gauge32
    MAX-ACCESS   read-only
    STATUS       current
    DESCRIPTION
        "Cisco Firepower equipment:RackFanModuleDef:fanCapacity
        managed object property"
    ::= { cfprEquipmentRackFanModuleDefEntry 5 }

cfprEquipmentRackFanModuleDefIntId OBJECT-TYPE
    SYNTAX       SnmpAdminString
    MAX-ACCESS   read-only
    STATUS       current
    DESCRIPTION
        "Cisco Firepower equipment:RackFanModuleDef:intId
        managed object property"
    ::= { cfprEquipmentRackFanModuleDefEntry 6 }

cfprEquipmentRackFanModuleDefName OBJECT-TYPE
    SYNTAX       SnmpAdminString
    MAX-ACCESS   read-only
    STATUS       current
    DESCRIPTION
        "Cisco Firepower equipment:RackFanModuleDef:name
        managed object property"
    ::= { cfprEquipmentRackFanModuleDefEntry 7 }

cfprEquipmentRackFanModuleDefPolicyLevel OBJECT-TYPE
    SYNTAX       Gauge32
    MAX-ACCESS   read-only
    STATUS       current
    DESCRIPTION
        "Cisco Firepower equipment:RackFanModuleDef:policyLevel
        managed object property"
    ::= { cfprEquipmentRackFanModuleDefEntry 8 }

cfprEquipmentRackFanModuleDefPolicyOwner OBJECT-TYPE
    SYNTAX       CfprPolicyPolicyOwner
    MAX-ACCESS   read-only
    STATUS       current
    DESCRIPTION
        "Cisco Firepower equipment:RackFanModuleDef:policyOwner
        managed object property"
    ::= { cfprEquipmentRackFanModuleDefEntry 9 }

cfprEquipmentRackUnitCapProviderTable OBJECT-TYPE
    SYNTAX           SEQUENCE OF CfprEquipmentRackUnitCapProviderEntry
    MAX-ACCESS       not-accessible
    STATUS           current
    DESCRIPTION
        "Cisco Firepower equipment:RackUnitCapProvider
        managed object table"
    ::= { cfprEquipmentObjects 119 }

cfprEquipmentRackUnitCapProviderEntry OBJECT-TYPE
    SYNTAX           CfprEquipmentRackUnitCapProviderEntry
    MAX-ACCESS       not-accessible
    STATUS           current
    DESCRIPTION
        "Entry for the cfprEquipmentRackUnitCapProviderTable table."
    INDEX { cfprEquipmentRackUnitCapProviderInstanceId }
    ::= { cfprEquipmentRackUnitCapProviderTable 1 }

CfprEquipmentRackUnitCapProviderEntry ::= SEQUENCE {
    cfprEquipmentRackUnitCapProviderInstanceId                       CfprManagedObjectId,
    cfprEquipmentRackUnitCapProviderDn                               CfprManagedObjectDn,
    cfprEquipmentRackUnitCapProviderRn                               SnmpAdminString,
    cfprEquipmentRackUnitCapProviderDeleted                          TruthValue,
    cfprEquipmentRackUnitCapProviderDeprecated                       TruthValue,
    cfprEquipmentRackUnitCapProviderElementLoadFailures              Gauge32,
    cfprEquipmentRackUnitCapProviderElementsLoaded                   Gauge32,
    cfprEquipmentRackUnitCapProviderGencount                         Gauge32,
    cfprEquipmentRackUnitCapProviderLoadErrors                       Gauge32,
    cfprEquipmentRackUnitCapProviderLoadWarnings                     Gauge32,
    cfprEquipmentRackUnitCapProviderMaxLocalDisks                    Gauge32,
    cfprEquipmentRackUnitCapProviderMgmtPlaneVer                     SnmpAdminString,
    cfprEquipmentRackUnitCapProviderModel                            SnmpAdminString,
    cfprEquipmentRackUnitCapProviderPromCardType                     Gauge32,
    cfprEquipmentRackUnitCapProviderRevision                         SnmpAdminString,
    cfprEquipmentRackUnitCapProviderVendor                           SnmpAdminString
}

cfprEquipmentRackUnitCapProviderInstanceId OBJECT-TYPE
    SYNTAX       CfprManagedObjectId
    MAX-ACCESS   not-accessible
    STATUS       current
    DESCRIPTION
        "Instance identifier of the managed object."
    ::= { cfprEquipmentRackUnitCapProviderEntry 1 }

cfprEquipmentRackUnitCapProviderDn OBJECT-TYPE
    SYNTAX       CfprManagedObjectDn
    MAX-ACCESS   read-only
    STATUS       current
    DESCRIPTION
        "Cisco Firepower equipment:RackUnitCapProvider:dn
        managed object property"
    ::= { cfprEquipmentRackUnitCapProviderEntry 2 }

cfprEquipmentRackUnitCapProviderRn OBJECT-TYPE
    SYNTAX       SnmpAdminString
    MAX-ACCESS   read-only
    STATUS       current
    DESCRIPTION
        "Cisco Firepower equipment:RackUnitCapProvider:rn
        managed object property"
    ::= { cfprEquipmentRackUnitCapProviderEntry 3 }

cfprEquipmentRackUnitCapProviderDeleted OBJECT-TYPE
    SYNTAX       TruthValue
    MAX-ACCESS   read-only
    STATUS       current
    DESCRIPTION
        "Cisco Firepower equipment:RackUnitCapProvider:deleted
        managed object property"
    ::= { cfprEquipmentRackUnitCapProviderEntry 4 }

cfprEquipmentRackUnitCapProviderDeprecated OBJECT-TYPE
    SYNTAX       TruthValue
    MAX-ACCESS   read-only
    STATUS       current
    DESCRIPTION
        "Cisco Firepower equipment:RackUnitCapProvider:deprecated
        managed object property"
    ::= { cfprEquipmentRackUnitCapProviderEntry 5 }

cfprEquipmentRackUnitCapProviderElementLoadFailures OBJECT-TYPE
    SYNTAX       Gauge32
    MAX-ACCESS   read-only
    STATUS       current
    DESCRIPTION
        "Cisco Firepower equipment:RackUnitCapProvider:elementLoadFailures
         managed object property"
    ::= { cfprEquipmentRackUnitCapProviderEntry 6 }

cfprEquipmentRackUnitCapProviderElementsLoaded OBJECT-TYPE
    SYNTAX       Gauge32
    MAX-ACCESS   read-only
    STATUS       current
    DESCRIPTION
        "Cisco Firepower equipment:RackUnitCapProvider:elementsLoaded
        managed object property"
    ::= { cfprEquipmentRackUnitCapProviderEntry 7 }

cfprEquipmentRackUnitCapProviderGencount OBJECT-TYPE
    SYNTAX       Gauge32
    MAX-ACCESS   read-only
    STATUS       current
    DESCRIPTION
        "Cisco Firepower equipment:RackUnitCapProvider:gencount
        managed object property"
    ::= { cfprEquipmentRackUnitCapProviderEntry 8 }

cfprEquipmentRackUnitCapProviderLoadErrors OBJECT-TYPE
    SYNTAX       Gauge32
    MAX-ACCESS   read-only
    STATUS       current
    DESCRIPTION
        "Cisco Firepower equipment:RackUnitCapProvider:loadErrors
        managed object property"
    ::= { cfprEquipmentRackUnitCapProviderEntry 9 }

cfprEquipmentRackUnitCapProviderLoadWarnings OBJECT-TYPE
    SYNTAX       Gauge32
    MAX-ACCESS   read-only
    STATUS       current
    DESCRIPTION
        "Cisco Firepower equipment:RackUnitCapProvider:loadWarnings
        managed object property"
    ::= { cfprEquipmentRackUnitCapProviderEntry 10 }

cfprEquipmentRackUnitCapProviderMaxLocalDisks OBJECT-TYPE
    SYNTAX       Gauge32
    MAX-ACCESS   read-only
    STATUS       current
    DESCRIPTION
        "Cisco Firepower equipment:RackUnitCapProvider:maxLocalDisks
        managed object property"
    ::= { cfprEquipmentRackUnitCapProviderEntry 11 }

cfprEquipmentRackUnitCapProviderMgmtPlaneVer OBJECT-TYPE
    SYNTAX       SnmpAdminString
    MAX-ACCESS   read-only
    STATUS       current
    DESCRIPTION
        "Cisco Firepower equipment:RackUnitCapProvider:mgmtPlaneVer
        managed object property"
    ::= { cfprEquipmentRackUnitCapProviderEntry 12 }

cfprEquipmentRackUnitCapProviderModel OBJECT-TYPE
    SYNTAX       SnmpAdminString
    MAX-ACCESS   read-only
    STATUS       current
    DESCRIPTION
        "Cisco Firepower equipment:RackUnitCapProvider:model
        managed object property"
    ::= { cfprEquipmentRackUnitCapProviderEntry 13 }

cfprEquipmentRackUnitCapProviderPromCardType OBJECT-TYPE
    SYNTAX       Gauge32
    MAX-ACCESS   read-only
    STATUS       current
    DESCRIPTION
        "Cisco Firepower equipment:RackUnitCapProvider:promCardType
        managed object property"
    ::= { cfprEquipmentRackUnitCapProviderEntry 14 }

cfprEquipmentRackUnitCapProviderRevision OBJECT-TYPE
    SYNTAX       SnmpAdminString
    MAX-ACCESS   read-only
    STATUS       current
    DESCRIPTION
        "Cisco Firepower equipment:RackUnitCapProvider:revision
        managed object property"
    ::= { cfprEquipmentRackUnitCapProviderEntry 15 }

cfprEquipmentRackUnitCapProviderVendor OBJECT-TYPE
    SYNTAX       SnmpAdminString
    MAX-ACCESS   read-only
    STATUS       current
    DESCRIPTION
        "Cisco Firepower equipment:RackUnitCapProvider:vendor
        managed object property"
    ::= { cfprEquipmentRackUnitCapProviderEntry 16 }

cfprEquipmentRackUnitFanStatsTable OBJECT-TYPE
    SYNTAX           SEQUENCE OF CfprEquipmentRackUnitFanStatsEntry
    MAX-ACCESS       not-accessible
    STATUS           current
    DESCRIPTION
        "Cisco Firepower equipment:RackUnitFanStats managed object table"
    ::= { cfprEquipmentObjects 120 }

cfprEquipmentRackUnitFanStatsEntry OBJECT-TYPE
    SYNTAX           CfprEquipmentRackUnitFanStatsEntry
    MAX-ACCESS       not-accessible
    STATUS           current
    DESCRIPTION
        "Entry for the cfprEquipmentRackUnitFanStatsTable table."
    INDEX { cfprEquipmentRackUnitFanStatsInstanceId }
    ::= { cfprEquipmentRackUnitFanStatsTable 1 }

CfprEquipmentRackUnitFanStatsEntry ::= SEQUENCE {
    cfprEquipmentRackUnitFanStatsInstanceId                          CfprManagedObjectId,
    cfprEquipmentRackUnitFanStatsDn                                  CfprManagedObjectDn,
    cfprEquipmentRackUnitFanStatsRn                                  SnmpAdminString,
    cfprEquipmentRackUnitFanStatsIntervals                           Gauge32,
    cfprEquipmentRackUnitFanStatsSpeed                               Gauge32,
    cfprEquipmentRackUnitFanStatsSpeedAvg                            Gauge32,
    cfprEquipmentRackUnitFanStatsSpeedMax                            Gauge32,
    cfprEquipmentRackUnitFanStatsSpeedMin                            Gauge32,
    cfprEquipmentRackUnitFanStatsSuspect                             TruthValue,
    cfprEquipmentRackUnitFanStatsThresholded                         CfprEquipmentRackUnitFanStatsThresholded,
    cfprEquipmentRackUnitFanStatsTimeCollected                       DateAndTime,
    cfprEquipmentRackUnitFanStatsUpdate                              Gauge32
}

cfprEquipmentRackUnitFanStatsInstanceId OBJECT-TYPE
    SYNTAX       CfprManagedObjectId
    MAX-ACCESS   not-accessible
    STATUS       current
    DESCRIPTION
        "Instance identifier of the managed object."
    ::= { cfprEquipmentRackUnitFanStatsEntry 1 }

cfprEquipmentRackUnitFanStatsDn OBJECT-TYPE
    SYNTAX       CfprManagedObjectDn
    MAX-ACCESS   read-only
    STATUS       current
    DESCRIPTION
        "Cisco Firepower equipment:RackUnitFanStats:dn
        managed object property"
    ::= { cfprEquipmentRackUnitFanStatsEntry 2 }

cfprEquipmentRackUnitFanStatsRn OBJECT-TYPE
    SYNTAX       SnmpAdminString
    MAX-ACCESS   read-only
    STATUS       current
    DESCRIPTION
        "Cisco Firepower equipment:RackUnitFanStats:rn
        managed object property"
    ::= { cfprEquipmentRackUnitFanStatsEntry 3 }

cfprEquipmentRackUnitFanStatsIntervals OBJECT-TYPE
    SYNTAX       Gauge32
    MAX-ACCESS   read-only
    STATUS       current
    DESCRIPTION
        "Cisco Firepower equipment:RackUnitFanStats:intervals
        managed object property"
    ::= { cfprEquipmentRackUnitFanStatsEntry 4 }

cfprEquipmentRackUnitFanStatsSpeed OBJECT-TYPE
    SYNTAX       Gauge32
    MAX-ACCESS   read-only
    STATUS       current
    DESCRIPTION
        "Cisco Firepower equipment:RackUnitFanStats:speed
        managed object property"
    ::= { cfprEquipmentRackUnitFanStatsEntry 5 }

cfprEquipmentRackUnitFanStatsSpeedAvg OBJECT-TYPE
    SYNTAX       Gauge32
    MAX-ACCESS   read-only
    STATUS       current
    DESCRIPTION
        "Cisco Firepower equipment:RackUnitFanStats:speedAvg
        managed object property"
    ::= { cfprEquipmentRackUnitFanStatsEntry 6 }

cfprEquipmentRackUnitFanStatsSpeedMax OBJECT-TYPE
    SYNTAX       Gauge32
    MAX-ACCESS   read-only
    STATUS       current
    DESCRIPTION
        "Cisco Firepower equipment:RackUnitFanStats:speedMax
        managed object property"
    ::= { cfprEquipmentRackUnitFanStatsEntry 7 }

cfprEquipmentRackUnitFanStatsSpeedMin OBJECT-TYPE
    SYNTAX       Gauge32
    MAX-ACCESS   read-only
    STATUS       current
    DESCRIPTION
        "Cisco Firepower equipment:RackUnitFanStats:speedMin
        managed object property"
    ::= { cfprEquipmentRackUnitFanStatsEntry 8 }

cfprEquipmentRackUnitFanStatsSuspect OBJECT-TYPE
    SYNTAX       TruthValue
    MAX-ACCESS   read-only
    STATUS       current
    DESCRIPTION
        "Cisco Firepower equipment:RackUnitFanStats:suspect
        managed object property"
    ::= { cfprEquipmentRackUnitFanStatsEntry 9 }

cfprEquipmentRackUnitFanStatsThresholded OBJECT-TYPE
    SYNTAX       CfprEquipmentRackUnitFanStatsThresholded
    MAX-ACCESS   read-only
    STATUS       current
    DESCRIPTION
        "Cisco Firepower equipment:RackUnitFanStats:thresholded
        managed object property"
    ::= { cfprEquipmentRackUnitFanStatsEntry 10 }

cfprEquipmentRackUnitFanStatsTimeCollected OBJECT-TYPE
    SYNTAX       DateAndTime
    MAX-ACCESS   read-only
    STATUS       current
    DESCRIPTION
        "Cisco Firepower equipment:RackUnitFanStats:timeCollected
        managed object property"
    ::= { cfprEquipmentRackUnitFanStatsEntry 11 }

cfprEquipmentRackUnitFanStatsUpdate OBJECT-TYPE
    SYNTAX       Gauge32
    MAX-ACCESS   read-only
    STATUS       current
    DESCRIPTION
        "Cisco Firepower equipment:RackUnitFanStats:update
        managed object property"
    ::= { cfprEquipmentRackUnitFanStatsEntry 12 }

cfprEquipmentRackUnitFanStatsHistTable OBJECT-TYPE
    SYNTAX           SEQUENCE OF CfprEquipmentRackUnitFanStatsHistEntry
    MAX-ACCESS       not-accessible
    STATUS           current
    DESCRIPTION
        "Cisco Firepower equipment:RackUnitFanStatsHist
        managed object table"
    ::= { cfprEquipmentObjects 121 }

cfprEquipmentRackUnitFanStatsHistEntry OBJECT-TYPE
    SYNTAX           CfprEquipmentRackUnitFanStatsHistEntry
    MAX-ACCESS       not-accessible
    STATUS           current
    DESCRIPTION
        "Entry for the cfprEquipmentRackUnitFanStatsHistTable table."
    INDEX { cfprEquipmentRackUnitFanStatsHistInstanceId }
    ::= { cfprEquipmentRackUnitFanStatsHistTable 1 }

CfprEquipmentRackUnitFanStatsHistEntry ::= SEQUENCE {
    cfprEquipmentRackUnitFanStatsHistInstanceId                      CfprManagedObjectId,
    cfprEquipmentRackUnitFanStatsHistDn                              CfprManagedObjectDn,
    cfprEquipmentRackUnitFanStatsHistRn                              SnmpAdminString,
    cfprEquipmentRackUnitFanStatsHistId                              Unsigned64,
    cfprEquipmentRackUnitFanStatsHistMostRecent                      TruthValue,
    cfprEquipmentRackUnitFanStatsHistSpeed                           Gauge32,
    cfprEquipmentRackUnitFanStatsHistSpeedAvg                        Gauge32,
    cfprEquipmentRackUnitFanStatsHistSpeedMax                        Gauge32,
    cfprEquipmentRackUnitFanStatsHistSpeedMin                        Gauge32,
    cfprEquipmentRackUnitFanStatsHistSuspect                         TruthValue,
    cfprEquipmentRackUnitFanStatsHistThresholded                     CfprEquipmentRackUnitFanStatsHistThresholded,
    cfprEquipmentRackUnitFanStatsHistTimeCollected                   DateAndTime
}

cfprEquipmentRackUnitFanStatsHistInstanceId OBJECT-TYPE
    SYNTAX       CfprManagedObjectId
    MAX-ACCESS   not-accessible
    STATUS       current
    DESCRIPTION
        "Instance identifier of the managed object."
    ::= { cfprEquipmentRackUnitFanStatsHistEntry 1 }

cfprEquipmentRackUnitFanStatsHistDn OBJECT-TYPE
    SYNTAX       CfprManagedObjectDn
    MAX-ACCESS   read-only
    STATUS       current
    DESCRIPTION
        "Cisco Firepower equipment:RackUnitFanStatsHist:dn
        managed object property"
    ::= { cfprEquipmentRackUnitFanStatsHistEntry 2 }

cfprEquipmentRackUnitFanStatsHistRn OBJECT-TYPE
    SYNTAX       SnmpAdminString
    MAX-ACCESS   read-only
    STATUS       current
    DESCRIPTION
        "Cisco Firepower equipment:RackUnitFanStatsHist:rn
        managed object property"
    ::= { cfprEquipmentRackUnitFanStatsHistEntry 3 }

cfprEquipmentRackUnitFanStatsHistId OBJECT-TYPE
    SYNTAX       Unsigned64
    MAX-ACCESS   read-only
    STATUS       current
    DESCRIPTION
        "Cisco Firepower equipment:RackUnitFanStatsHist:id
        managed object property"
    ::= { cfprEquipmentRackUnitFanStatsHistEntry 4 }

cfprEquipmentRackUnitFanStatsHistMostRecent OBJECT-TYPE
    SYNTAX       TruthValue
    MAX-ACCESS   read-only
    STATUS       current
    DESCRIPTION
        "Cisco Firepower equipment:RackUnitFanStatsHist:mostRecent
        managed object property"
    ::= { cfprEquipmentRackUnitFanStatsHistEntry 5 }

cfprEquipmentRackUnitFanStatsHistSpeed OBJECT-TYPE
    SYNTAX       Gauge32
    MAX-ACCESS   read-only
    STATUS       current
    DESCRIPTION
        "Cisco Firepower equipment:RackUnitFanStatsHist:speed
        managed object property"
    ::= { cfprEquipmentRackUnitFanStatsHistEntry 6 }

cfprEquipmentRackUnitFanStatsHistSpeedAvg OBJECT-TYPE
    SYNTAX       Gauge32
    MAX-ACCESS   read-only
    STATUS       current
    DESCRIPTION
        "Cisco Firepower equipment:RackUnitFanStatsHist:speedAvg
        managed object property"
    ::= { cfprEquipmentRackUnitFanStatsHistEntry 7 }

cfprEquipmentRackUnitFanStatsHistSpeedMax OBJECT-TYPE
    SYNTAX       Gauge32
    MAX-ACCESS   read-only
    STATUS       current
    DESCRIPTION
        "Cisco Firepower equipment:RackUnitFanStatsHist:speedMax
        managed object property"
    ::= { cfprEquipmentRackUnitFanStatsHistEntry 8 }

cfprEquipmentRackUnitFanStatsHistSpeedMin OBJECT-TYPE
    SYNTAX       Gauge32
    MAX-ACCESS   read-only
    STATUS       current
    DESCRIPTION
        "Cisco Firepower equipment:RackUnitFanStatsHist:speedMin
        managed object property"
    ::= { cfprEquipmentRackUnitFanStatsHistEntry 9 }

cfprEquipmentRackUnitFanStatsHistSuspect OBJECT-TYPE
    SYNTAX       TruthValue
    MAX-ACCESS   read-only
    STATUS       current
    DESCRIPTION
        "Cisco Firepower equipment:RackUnitFanStatsHist:suspect
        managed object property"
    ::= { cfprEquipmentRackUnitFanStatsHistEntry 10 }

cfprEquipmentRackUnitFanStatsHistThresholded OBJECT-TYPE
    SYNTAX       CfprEquipmentRackUnitFanStatsHistThresholded
    MAX-ACCESS   read-only
    STATUS       current
    DESCRIPTION
        "Cisco Firepower equipment:RackUnitFanStatsHist:thresholded
        managed object property"
    ::= { cfprEquipmentRackUnitFanStatsHistEntry 11 }

cfprEquipmentRackUnitFanStatsHistTimeCollected OBJECT-TYPE
    SYNTAX       DateAndTime
    MAX-ACCESS   read-only
    STATUS       current
    DESCRIPTION
        "Cisco Firepower equipment:RackUnitFanStatsHist:timeCollected
        managed object property"
    ::= { cfprEquipmentRackUnitFanStatsHistEntry 12 }

cfprEquipmentRackUnitPsuStatsTable OBJECT-TYPE
    SYNTAX           SEQUENCE OF CfprEquipmentRackUnitPsuStatsEntry
    MAX-ACCESS       not-accessible
    STATUS           current
    DESCRIPTION
        "Cisco Firepower equipment:RackUnitPsuStats managed object table"
    ::= { cfprEquipmentObjects 122 }

cfprEquipmentRackUnitPsuStatsEntry OBJECT-TYPE
    SYNTAX           CfprEquipmentRackUnitPsuStatsEntry
    MAX-ACCESS       not-accessible
    STATUS           current
    DESCRIPTION
        "Entry for the cfprEquipmentRackUnitPsuStatsTable table."
    INDEX { cfprEquipmentRackUnitPsuStatsInstanceId }
    ::= { cfprEquipmentRackUnitPsuStatsTable 1 }

CfprEquipmentRackUnitPsuStatsEntry ::= SEQUENCE {
    cfprEquipmentRackUnitPsuStatsInstanceId                          CfprManagedObjectId,
    cfprEquipmentRackUnitPsuStatsDn                                  CfprManagedObjectDn,
    cfprEquipmentRackUnitPsuStatsRn                                  SnmpAdminString,
    cfprEquipmentRackUnitPsuStatsAmbientTemp                         INTEGER,
    cfprEquipmentRackUnitPsuStatsAmbientTempAvg                      INTEGER,
    cfprEquipmentRackUnitPsuStatsAmbientTempMax                      INTEGER,
    cfprEquipmentRackUnitPsuStatsAmbientTempMin                      INTEGER,
    cfprEquipmentRackUnitPsuStatsInputPower                          INTEGER,
    cfprEquipmentRackUnitPsuStatsInputPowerAvg                       INTEGER,
    cfprEquipmentRackUnitPsuStatsInputPowerMax                       INTEGER,
    cfprEquipmentRackUnitPsuStatsInputPowerMin                       INTEGER,
    cfprEquipmentRackUnitPsuStatsInputVoltage                        INTEGER,
    cfprEquipmentRackUnitPsuStatsInputVoltageAvg                     INTEGER,
    cfprEquipmentRackUnitPsuStatsInputVoltageMax                     INTEGER,
    cfprEquipmentRackUnitPsuStatsInputVoltageMin                     INTEGER,
    cfprEquipmentRackUnitPsuStatsIntervals                           Gauge32,
    cfprEquipmentRackUnitPsuStatsOutputCurrent                       INTEGER,
    cfprEquipmentRackUnitPsuStatsOutputCurrentAvg                    INTEGER,
    cfprEquipmentRackUnitPsuStatsOutputCurrentMax                    INTEGER,
    cfprEquipmentRackUnitPsuStatsOutputCurrentMin                    INTEGER,
    cfprEquipmentRackUnitPsuStatsOutputPower                         INTEGER,
    cfprEquipmentRackUnitPsuStatsOutputPowerAvg                      INTEGER,
    cfprEquipmentRackUnitPsuStatsOutputPowerMax                      INTEGER,
    cfprEquipmentRackUnitPsuStatsOutputPowerMin                      INTEGER,
    cfprEquipmentRackUnitPsuStatsOutputVoltage                       INTEGER,
    cfprEquipmentRackUnitPsuStatsOutputVoltageAvg                    INTEGER,
    cfprEquipmentRackUnitPsuStatsOutputVoltageMax                    INTEGER,
    cfprEquipmentRackUnitPsuStatsOutputVoltageMin                    INTEGER,
    cfprEquipmentRackUnitPsuStatsSuspect                             TruthValue,
    cfprEquipmentRackUnitPsuStatsThresholded                         CfprEquipmentRackUnitPsuStatsThresholded,
    cfprEquipmentRackUnitPsuStatsTimeCollected                       DateAndTime,
    cfprEquipmentRackUnitPsuStatsUpdate                              Gauge32
}

cfprEquipmentRackUnitPsuStatsInstanceId OBJECT-TYPE
    SYNTAX       CfprManagedObjectId
    MAX-ACCESS   not-accessible
    STATUS       current
    DESCRIPTION
        "Instance identifier of the managed object."
    ::= { cfprEquipmentRackUnitPsuStatsEntry 1 }

cfprEquipmentRackUnitPsuStatsDn OBJECT-TYPE
    SYNTAX       CfprManagedObjectDn
    MAX-ACCESS   read-only
    STATUS       current
    DESCRIPTION
        "Cisco Firepower equipment:RackUnitPsuStats:dn
        managed object property"
    ::= { cfprEquipmentRackUnitPsuStatsEntry 2 }

cfprEquipmentRackUnitPsuStatsRn OBJECT-TYPE
    SYNTAX       SnmpAdminString
    MAX-ACCESS   read-only
    STATUS       current
    DESCRIPTION
        "Cisco Firepower equipment:RackUnitPsuStats:rn
        managed object property"
    ::= { cfprEquipmentRackUnitPsuStatsEntry 3 }

cfprEquipmentRackUnitPsuStatsAmbientTemp OBJECT-TYPE
    SYNTAX       INTEGER
    MAX-ACCESS   read-only
    STATUS       current
    DESCRIPTION
        "Cisco Firepower equipment:RackUnitPsuStats:ambientTemp
        managed object property"
    ::= { cfprEquipmentRackUnitPsuStatsEntry 4 }

cfprEquipmentRackUnitPsuStatsAmbientTempAvg OBJECT-TYPE
    SYNTAX       INTEGER
    MAX-ACCESS   read-only
    STATUS       current
    DESCRIPTION
        "Cisco Firepower equipment:RackUnitPsuStats:ambientTempAvg
        managed object property"
    ::= { cfprEquipmentRackUnitPsuStatsEntry 5 }

cfprEquipmentRackUnitPsuStatsAmbientTempMax OBJECT-TYPE
    SYNTAX       INTEGER
    MAX-ACCESS   read-only
    STATUS       current
    DESCRIPTION
        "Cisco Firepower equipment:RackUnitPsuStats:ambientTempMax
        managed object property"
    ::= { cfprEquipmentRackUnitPsuStatsEntry 6 }

cfprEquipmentRackUnitPsuStatsAmbientTempMin OBJECT-TYPE
    SYNTAX       INTEGER
    MAX-ACCESS   read-only
    STATUS       current
    DESCRIPTION
        "Cisco Firepower equipment:RackUnitPsuStats:ambientTempMin
        managed object property"
    ::= { cfprEquipmentRackUnitPsuStatsEntry 7 }

cfprEquipmentRackUnitPsuStatsInputPower OBJECT-TYPE
    SYNTAX       INTEGER
    MAX-ACCESS   read-only
    STATUS       current
    DESCRIPTION
        "Cisco Firepower equipment:RackUnitPsuStats:inputPower
        managed object property"
    ::= { cfprEquipmentRackUnitPsuStatsEntry 8 }

cfprEquipmentRackUnitPsuStatsInputPowerAvg OBJECT-TYPE
    SYNTAX       INTEGER
    MAX-ACCESS   read-only
    STATUS       current
    DESCRIPTION
        "Cisco Firepower equipment:RackUnitPsuStats:inputPowerAvg
        managed object property"
    ::= { cfprEquipmentRackUnitPsuStatsEntry 9 }

cfprEquipmentRackUnitPsuStatsInputPowerMax OBJECT-TYPE
    SYNTAX       INTEGER
    MAX-ACCESS   read-only
    STATUS       current
    DESCRIPTION
        "Cisco Firepower equipment:RackUnitPsuStats:inputPowerMax
        managed object property"
    ::= { cfprEquipmentRackUnitPsuStatsEntry 10 }

cfprEquipmentRackUnitPsuStatsInputPowerMin OBJECT-TYPE
    SYNTAX       INTEGER
    MAX-ACCESS   read-only
    STATUS       current
    DESCRIPTION
        "Cisco Firepower equipment:RackUnitPsuStats:inputPowerMin
        managed object property"
    ::= { cfprEquipmentRackUnitPsuStatsEntry 11 }

cfprEquipmentRackUnitPsuStatsInputVoltage OBJECT-TYPE
    SYNTAX       INTEGER
    MAX-ACCESS   read-only
    STATUS       current
    DESCRIPTION
        "Cisco Firepower equipment:RackUnitPsuStats:inputVoltage
        managed object property"
    ::= { cfprEquipmentRackUnitPsuStatsEntry 12 }

cfprEquipmentRackUnitPsuStatsInputVoltageAvg OBJECT-TYPE
    SYNTAX       INTEGER
    MAX-ACCESS   read-only
    STATUS       current
    DESCRIPTION
        "Cisco Firepower equipment:RackUnitPsuStats:inputVoltageAvg
        managed object property"
    ::= { cfprEquipmentRackUnitPsuStatsEntry 13 }

cfprEquipmentRackUnitPsuStatsInputVoltageMax OBJECT-TYPE
    SYNTAX       INTEGER
    MAX-ACCESS   read-only
    STATUS       current
    DESCRIPTION
        "Cisco Firepower equipment:RackUnitPsuStats:inputVoltageMax
        managed object property"
    ::= { cfprEquipmentRackUnitPsuStatsEntry 14 }

cfprEquipmentRackUnitPsuStatsInputVoltageMin OBJECT-TYPE
    SYNTAX       INTEGER
    MAX-ACCESS   read-only
    STATUS       current
    DESCRIPTION
        "Cisco Firepower equipment:RackUnitPsuStats:inputVoltageMin
        managed object property"
    ::= { cfprEquipmentRackUnitPsuStatsEntry 15 }

cfprEquipmentRackUnitPsuStatsIntervals OBJECT-TYPE
    SYNTAX       Gauge32
    MAX-ACCESS   read-only
    STATUS       current
    DESCRIPTION
        "Cisco Firepower equipment:RackUnitPsuStats:intervals
        managed object property"
    ::= { cfprEquipmentRackUnitPsuStatsEntry 16 }

cfprEquipmentRackUnitPsuStatsOutputCurrent OBJECT-TYPE
    SYNTAX       INTEGER
    MAX-ACCESS   read-only
    STATUS       current
    DESCRIPTION
        "Cisco Firepower equipment:RackUnitPsuStats:outputCurrent
        managed object property"
    ::= { cfprEquipmentRackUnitPsuStatsEntry 17 }

cfprEquipmentRackUnitPsuStatsOutputCurrentAvg OBJECT-TYPE
    SYNTAX       INTEGER
    MAX-ACCESS   read-only
    STATUS       current
    DESCRIPTION
        "Cisco Firepower equipment:RackUnitPsuStats:outputCurrentAvg
        managed object property"
    ::= { cfprEquipmentRackUnitPsuStatsEntry 18 }

cfprEquipmentRackUnitPsuStatsOutputCurrentMax OBJECT-TYPE
    SYNTAX       INTEGER
    MAX-ACCESS   read-only
    STATUS       current
    DESCRIPTION
        "Cisco Firepower equipment:RackUnitPsuStats:outputCurrentMax
        managed object property"
    ::= { cfprEquipmentRackUnitPsuStatsEntry 19 }

cfprEquipmentRackUnitPsuStatsOutputCurrentMin OBJECT-TYPE
    SYNTAX       INTEGER
    MAX-ACCESS   read-only
    STATUS       current
    DESCRIPTION
        "Cisco Firepower equipment:RackUnitPsuStats:outputCurrentMin
        managed object property"
    ::= { cfprEquipmentRackUnitPsuStatsEntry 20 }

cfprEquipmentRackUnitPsuStatsOutputPower OBJECT-TYPE
    SYNTAX       INTEGER
    MAX-ACCESS   read-only
    STATUS       current
    DESCRIPTION
        "Cisco Firepower equipment:RackUnitPsuStats:outputPower
        managed object property"
    ::= { cfprEquipmentRackUnitPsuStatsEntry 21 }

cfprEquipmentRackUnitPsuStatsOutputPowerAvg OBJECT-TYPE
    SYNTAX       INTEGER
    MAX-ACCESS   read-only
    STATUS       current
    DESCRIPTION
        "Cisco Firepower equipment:RackUnitPsuStats:outputPowerAvg
        managed object property"
    ::= { cfprEquipmentRackUnitPsuStatsEntry 22 }

cfprEquipmentRackUnitPsuStatsOutputPowerMax OBJECT-TYPE
    SYNTAX       INTEGER
    MAX-ACCESS   read-only
    STATUS       current
    DESCRIPTION
        "Cisco Firepower equipment:RackUnitPsuStats:outputPowerMax
        managed object property"
    ::= { cfprEquipmentRackUnitPsuStatsEntry 23 }

cfprEquipmentRackUnitPsuStatsOutputPowerMin OBJECT-TYPE
    SYNTAX       INTEGER
    MAX-ACCESS   read-only
    STATUS       current
    DESCRIPTION
        "Cisco Firepower equipment:RackUnitPsuStats:outputPowerMin
        managed object property"
    ::= { cfprEquipmentRackUnitPsuStatsEntry 24 }

cfprEquipmentRackUnitPsuStatsOutputVoltage OBJECT-TYPE
    SYNTAX       INTEGER
    MAX-ACCESS   read-only
    STATUS       current
    DESCRIPTION
        "Cisco Firepower equipment:RackUnitPsuStats:outputVoltage
        managed object property"
    ::= { cfprEquipmentRackUnitPsuStatsEntry 25 }

cfprEquipmentRackUnitPsuStatsOutputVoltageAvg OBJECT-TYPE
    SYNTAX       INTEGER
    MAX-ACCESS   read-only
    STATUS       current
    DESCRIPTION
        "Cisco Firepower equipment:RackUnitPsuStats:outputVoltageAvg
        managed object property"
    ::= { cfprEquipmentRackUnitPsuStatsEntry 26 }

cfprEquipmentRackUnitPsuStatsOutputVoltageMax OBJECT-TYPE
    SYNTAX       INTEGER
    MAX-ACCESS   read-only
    STATUS       current
    DESCRIPTION
        "Cisco Firepower equipment:RackUnitPsuStats:outputVoltageMax
        managed object property"
    ::= { cfprEquipmentRackUnitPsuStatsEntry 27 }

cfprEquipmentRackUnitPsuStatsOutputVoltageMin OBJECT-TYPE
    SYNTAX       INTEGER
    MAX-ACCESS   read-only
    STATUS       current
    DESCRIPTION
        "Cisco Firepower equipment:RackUnitPsuStats:outputVoltageMin
        managed object property"
    ::= { cfprEquipmentRackUnitPsuStatsEntry 28 }

cfprEquipmentRackUnitPsuStatsSuspect OBJECT-TYPE
    SYNTAX       TruthValue
    MAX-ACCESS   read-only
    STATUS       current
    DESCRIPTION
        "Cisco Firepower equipment:RackUnitPsuStats:suspect
        managed object property"
    ::= { cfprEquipmentRackUnitPsuStatsEntry 29 }

cfprEquipmentRackUnitPsuStatsThresholded OBJECT-TYPE
    SYNTAX       CfprEquipmentRackUnitPsuStatsThresholded
    MAX-ACCESS   read-only
    STATUS       current
    DESCRIPTION
        "Cisco Firepower equipment:RackUnitPsuStats:thresholded
        managed object property"
    ::= { cfprEquipmentRackUnitPsuStatsEntry 30 }

cfprEquipmentRackUnitPsuStatsTimeCollected OBJECT-TYPE
    SYNTAX       DateAndTime
    MAX-ACCESS   read-only
    STATUS       current
    DESCRIPTION
        "Cisco Firepower equipment:RackUnitPsuStats:timeCollected
        managed object property"
    ::= { cfprEquipmentRackUnitPsuStatsEntry 31 }

cfprEquipmentRackUnitPsuStatsUpdate OBJECT-TYPE
    SYNTAX       Gauge32
    MAX-ACCESS   read-only
    STATUS       current
    DESCRIPTION
        "Cisco Firepower equipment:RackUnitPsuStats:update
        managed object property"
    ::= { cfprEquipmentRackUnitPsuStatsEntry 32 }

cfprEquipmentRackUnitPsuStatsHistTable OBJECT-TYPE
    SYNTAX           SEQUENCE OF CfprEquipmentRackUnitPsuStatsHistEntry
    MAX-ACCESS       not-accessible
    STATUS           current
    DESCRIPTION
        "Cisco Firepower equipment:RackUnitPsuStatsHist
        managed object table"
    ::= { cfprEquipmentObjects 123 }

cfprEquipmentRackUnitPsuStatsHistEntry OBJECT-TYPE
    SYNTAX           CfprEquipmentRackUnitPsuStatsHistEntry
    MAX-ACCESS       not-accessible
    STATUS           current
    DESCRIPTION
        "Entry for the cfprEquipmentRackUnitPsuStatsHistTable table."
    INDEX { cfprEquipmentRackUnitPsuStatsHistInstanceId }
    ::= { cfprEquipmentRackUnitPsuStatsHistTable 1 }

CfprEquipmentRackUnitPsuStatsHistEntry ::= SEQUENCE {
    cfprEquipmentRackUnitPsuStatsHistInstanceId                      CfprManagedObjectId,
    cfprEquipmentRackUnitPsuStatsHistDn                              CfprManagedObjectDn,
    cfprEquipmentRackUnitPsuStatsHistRn                              SnmpAdminString,
    cfprEquipmentRackUnitPsuStatsHistAmbientTemp                     INTEGER,
    cfprEquipmentRackUnitPsuStatsHistAmbientTempAvg                  INTEGER,
    cfprEquipmentRackUnitPsuStatsHistAmbientTempMax                  INTEGER,
    cfprEquipmentRackUnitPsuStatsHistAmbientTempMin                  INTEGER,
    cfprEquipmentRackUnitPsuStatsHistId                              Unsigned64,
    cfprEquipmentRackUnitPsuStatsHistInputPower                      INTEGER,
    cfprEquipmentRackUnitPsuStatsHistInputPowerAvg                   INTEGER,
    cfprEquipmentRackUnitPsuStatsHistInputPowerMax                   INTEGER,
    cfprEquipmentRackUnitPsuStatsHistInputPowerMin                   INTEGER,
    cfprEquipmentRackUnitPsuStatsHistInputVoltage                    INTEGER,
    cfprEquipmentRackUnitPsuStatsHistInputVoltageAvg                 INTEGER,
    cfprEquipmentRackUnitPsuStatsHistInputVoltageMax                 INTEGER,
    cfprEquipmentRackUnitPsuStatsHistInputVoltageMin                 INTEGER,
    cfprEquipmentRackUnitPsuStatsHistMostRecent                      TruthValue,
    cfprEquipmentRackUnitPsuStatsHistOutputCurrent                   INTEGER,
    cfprEquipmentRackUnitPsuStatsHistOutputCurrentAvg                INTEGER,
    cfprEquipmentRackUnitPsuStatsHistOutputCurrentMax                INTEGER,
    cfprEquipmentRackUnitPsuStatsHistOutputCurrentMin                INTEGER,
    cfprEquipmentRackUnitPsuStatsHistOutputPower                     INTEGER,
    cfprEquipmentRackUnitPsuStatsHistOutputPowerAvg                  INTEGER,
    cfprEquipmentRackUnitPsuStatsHistOutputPowerMax                  INTEGER,
    cfprEquipmentRackUnitPsuStatsHistOutputPowerMin                  INTEGER,
    cfprEquipmentRackUnitPsuStatsHistOutputVoltage                   INTEGER,
    cfprEquipmentRackUnitPsuStatsHistOutputVoltageAvg                INTEGER,
    cfprEquipmentRackUnitPsuStatsHistOutputVoltageMax                INTEGER,
    cfprEquipmentRackUnitPsuStatsHistOutputVoltageMin                INTEGER,
    cfprEquipmentRackUnitPsuStatsHistSuspect                         TruthValue,
    cfprEquipmentRackUnitPsuStatsHistThresholded                     CfprEquipmentRackUnitPsuStatsHistThresholded,
    cfprEquipmentRackUnitPsuStatsHistTimeCollected                   DateAndTime
}

cfprEquipmentRackUnitPsuStatsHistInstanceId OBJECT-TYPE
    SYNTAX       CfprManagedObjectId
    MAX-ACCESS   not-accessible
    STATUS       current
    DESCRIPTION
        "Instance identifier of the managed object."
    ::= { cfprEquipmentRackUnitPsuStatsHistEntry 1 }

cfprEquipmentRackUnitPsuStatsHistDn OBJECT-TYPE
    SYNTAX       CfprManagedObjectDn
    MAX-ACCESS   read-only
    STATUS       current
    DESCRIPTION
        "Cisco Firepower equipment:RackUnitPsuStatsHist:dn
        managed object property"
    ::= { cfprEquipmentRackUnitPsuStatsHistEntry 2 }

cfprEquipmentRackUnitPsuStatsHistRn OBJECT-TYPE
    SYNTAX       SnmpAdminString
    MAX-ACCESS   read-only
    STATUS       current
    DESCRIPTION
        "Cisco Firepower equipment:RackUnitPsuStatsHist:rn
        managed object property"
    ::= { cfprEquipmentRackUnitPsuStatsHistEntry 3 }

cfprEquipmentRackUnitPsuStatsHistAmbientTemp OBJECT-TYPE
    SYNTAX       INTEGER
    MAX-ACCESS   read-only
    STATUS       current
    DESCRIPTION
        "Cisco Firepower equipment:RackUnitPsuStatsHist:ambientTemp
        managed object property"
    ::= { cfprEquipmentRackUnitPsuStatsHistEntry 4 }

cfprEquipmentRackUnitPsuStatsHistAmbientTempAvg OBJECT-TYPE
    SYNTAX       INTEGER
    MAX-ACCESS   read-only
    STATUS       current
    DESCRIPTION
        "Cisco Firepower equipment:RackUnitPsuStatsHist:ambientTempAvg
        managed object property"
    ::= { cfprEquipmentRackUnitPsuStatsHistEntry 5 }

cfprEquipmentRackUnitPsuStatsHistAmbientTempMax OBJECT-TYPE
    SYNTAX       INTEGER
    MAX-ACCESS   read-only
    STATUS       current
    DESCRIPTION
        "Cisco Firepower equipment:RackUnitPsuStatsHist:ambientTempMax
        managed object property"
    ::= { cfprEquipmentRackUnitPsuStatsHistEntry 6 }

cfprEquipmentRackUnitPsuStatsHistAmbientTempMin OBJECT-TYPE
    SYNTAX       INTEGER
    MAX-ACCESS   read-only
    STATUS       current
    DESCRIPTION
        "Cisco Firepower equipment:RackUnitPsuStatsHist:ambientTempMin
        managed object property"
    ::= { cfprEquipmentRackUnitPsuStatsHistEntry 7 }

cfprEquipmentRackUnitPsuStatsHistId OBJECT-TYPE
    SYNTAX       Unsigned64
    MAX-ACCESS   read-only
    STATUS       current
    DESCRIPTION
        "Cisco Firepower equipment:RackUnitPsuStatsHist:id
        managed object property"
    ::= { cfprEquipmentRackUnitPsuStatsHistEntry 8 }

cfprEquipmentRackUnitPsuStatsHistInputPower OBJECT-TYPE
    SYNTAX       INTEGER
    MAX-ACCESS   read-only
    STATUS       current
    DESCRIPTION
        "Cisco Firepower equipment:RackUnitPsuStatsHist:inputPower
        managed object property"
    ::= { cfprEquipmentRackUnitPsuStatsHistEntry 9 }

cfprEquipmentRackUnitPsuStatsHistInputPowerAvg OBJECT-TYPE
    SYNTAX       INTEGER
    MAX-ACCESS   read-only
    STATUS       current
    DESCRIPTION
        "Cisco Firepower equipment:RackUnitPsuStatsHist:inputPowerAvg
        managed object property"
    ::= { cfprEquipmentRackUnitPsuStatsHistEntry 10 }

cfprEquipmentRackUnitPsuStatsHistInputPowerMax OBJECT-TYPE
    SYNTAX       INTEGER
    MAX-ACCESS   read-only
    STATUS       current
    DESCRIPTION
        "Cisco Firepower equipment:RackUnitPsuStatsHist:inputPowerMax
        managed object property"
    ::= { cfprEquipmentRackUnitPsuStatsHistEntry 11 }

cfprEquipmentRackUnitPsuStatsHistInputPowerMin OBJECT-TYPE
    SYNTAX       INTEGER
    MAX-ACCESS   read-only
    STATUS       current
    DESCRIPTION
        "Cisco Firepower equipment:RackUnitPsuStatsHist:inputPowerMin
        managed object property"
    ::= { cfprEquipmentRackUnitPsuStatsHistEntry 12 }

cfprEquipmentRackUnitPsuStatsHistInputVoltage OBJECT-TYPE
    SYNTAX       INTEGER
    MAX-ACCESS   read-only
    STATUS       current
    DESCRIPTION
        "Cisco Firepower equipment:RackUnitPsuStatsHist:inputVoltage
        managed object property"
    ::= { cfprEquipmentRackUnitPsuStatsHistEntry 13 }

cfprEquipmentRackUnitPsuStatsHistInputVoltageAvg OBJECT-TYPE
    SYNTAX       INTEGER
    MAX-ACCESS   read-only
    STATUS       current
    DESCRIPTION
        "Cisco Firepower equipment:RackUnitPsuStatsHist:inputVoltageAvg
        managed object property"
    ::= { cfprEquipmentRackUnitPsuStatsHistEntry 14 }

cfprEquipmentRackUnitPsuStatsHistInputVoltageMax OBJECT-TYPE
    SYNTAX       INTEGER
    MAX-ACCESS   read-only
    STATUS       current
    DESCRIPTION
        "Cisco Firepower equipment:RackUnitPsuStatsHist:inputVoltageMax
        managed object property"
    ::= { cfprEquipmentRackUnitPsuStatsHistEntry 15 }

cfprEquipmentRackUnitPsuStatsHistInputVoltageMin OBJECT-TYPE
    SYNTAX       INTEGER
    MAX-ACCESS   read-only
    STATUS       current
    DESCRIPTION
        "Cisco Firepower equipment:RackUnitPsuStatsHist:inputVoltageMin
        managed object property"
    ::= { cfprEquipmentRackUnitPsuStatsHistEntry 16 }

cfprEquipmentRackUnitPsuStatsHistMostRecent OBJECT-TYPE
    SYNTAX       TruthValue
    MAX-ACCESS   read-only
    STATUS       current
    DESCRIPTION
        "Cisco Firepower equipment:RackUnitPsuStatsHist:mostRecent
        managed object property"
    ::= { cfprEquipmentRackUnitPsuStatsHistEntry 17 }

cfprEquipmentRackUnitPsuStatsHistOutputCurrent OBJECT-TYPE
    SYNTAX       INTEGER
    MAX-ACCESS   read-only
    STATUS       current
    DESCRIPTION
        "Cisco Firepower equipment:RackUnitPsuStatsHist:outputCurrent
        managed object property"
    ::= { cfprEquipmentRackUnitPsuStatsHistEntry 18 }

cfprEquipmentRackUnitPsuStatsHistOutputCurrentAvg OBJECT-TYPE
    SYNTAX       INTEGER
    MAX-ACCESS   read-only
    STATUS       current
    DESCRIPTION
        "Cisco Firepower equipment:RackUnitPsuStatsHist:outputCurrentAvg
        managed object property"
    ::= { cfprEquipmentRackUnitPsuStatsHistEntry 19 }

cfprEquipmentRackUnitPsuStatsHistOutputCurrentMax OBJECT-TYPE
    SYNTAX       INTEGER
    MAX-ACCESS   read-only
    STATUS       current
    DESCRIPTION
        "Cisco Firepower equipment:RackUnitPsuStatsHist:outputCurrentMax
        managed object property"
    ::= { cfprEquipmentRackUnitPsuStatsHistEntry 20 }

cfprEquipmentRackUnitPsuStatsHistOutputCurrentMin OBJECT-TYPE
    SYNTAX       INTEGER
    MAX-ACCESS   read-only
    STATUS       current
    DESCRIPTION
        "Cisco Firepower equipment:RackUnitPsuStatsHist:outputCurrentMin
        managed object property"
    ::= { cfprEquipmentRackUnitPsuStatsHistEntry 21 }

cfprEquipmentRackUnitPsuStatsHistOutputPower OBJECT-TYPE
    SYNTAX       INTEGER
    MAX-ACCESS   read-only
    STATUS       current
    DESCRIPTION
        "Cisco Firepower equipment:RackUnitPsuStatsHist:outputPower
        managed object property"
    ::= { cfprEquipmentRackUnitPsuStatsHistEntry 22 }

cfprEquipmentRackUnitPsuStatsHistOutputPowerAvg OBJECT-TYPE
    SYNTAX       INTEGER
    MAX-ACCESS   read-only
    STATUS       current
    DESCRIPTION
        "Cisco Firepower equipment:RackUnitPsuStatsHist:outputPowerAvg
        managed object property"
    ::= { cfprEquipmentRackUnitPsuStatsHistEntry 23 }

cfprEquipmentRackUnitPsuStatsHistOutputPowerMax OBJECT-TYPE
    SYNTAX       INTEGER
    MAX-ACCESS   read-only
    STATUS       current
    DESCRIPTION
        "Cisco Firepower equipment:RackUnitPsuStatsHist:outputPowerMax
        managed object property"
    ::= { cfprEquipmentRackUnitPsuStatsHistEntry 24 }

cfprEquipmentRackUnitPsuStatsHistOutputPowerMin OBJECT-TYPE
    SYNTAX       INTEGER
    MAX-ACCESS   read-only
    STATUS       current
    DESCRIPTION
        "Cisco Firepower equipment:RackUnitPsuStatsHist:outputPowerMin
        managed object property"
    ::= { cfprEquipmentRackUnitPsuStatsHistEntry 25 }

cfprEquipmentRackUnitPsuStatsHistOutputVoltage OBJECT-TYPE
    SYNTAX       INTEGER
    MAX-ACCESS   read-only
    STATUS       current
    DESCRIPTION
        "Cisco Firepower equipment:RackUnitPsuStatsHist:outputVoltage
        managed object property"
    ::= { cfprEquipmentRackUnitPsuStatsHistEntry 26 }

cfprEquipmentRackUnitPsuStatsHistOutputVoltageAvg OBJECT-TYPE
    SYNTAX       INTEGER
    MAX-ACCESS   read-only
    STATUS       current
    DESCRIPTION
        "Cisco Firepower equipment:RackUnitPsuStatsHist:outputVoltageAvg
        managed object property"
    ::= { cfprEquipmentRackUnitPsuStatsHistEntry 27 }

cfprEquipmentRackUnitPsuStatsHistOutputVoltageMax OBJECT-TYPE
    SYNTAX       INTEGER
    MAX-ACCESS   read-only
    STATUS       current
    DESCRIPTION
        "Cisco Firepower equipment:RackUnitPsuStatsHist:outputVoltageMax
        managed object property"
    ::= { cfprEquipmentRackUnitPsuStatsHistEntry 28 }

cfprEquipmentRackUnitPsuStatsHistOutputVoltageMin OBJECT-TYPE
    SYNTAX       INTEGER
    MAX-ACCESS   read-only
    STATUS       current
    DESCRIPTION
        "Cisco Firepower equipment:RackUnitPsuStatsHist:outputVoltageMin
        managed object property"
    ::= { cfprEquipmentRackUnitPsuStatsHistEntry 29 }

cfprEquipmentRackUnitPsuStatsHistSuspect OBJECT-TYPE
    SYNTAX       TruthValue
    MAX-ACCESS   read-only
    STATUS       current
    DESCRIPTION
        "Cisco Firepower equipment:RackUnitPsuStatsHist:suspect
        managed object property"
    ::= { cfprEquipmentRackUnitPsuStatsHistEntry 30 }

cfprEquipmentRackUnitPsuStatsHistThresholded OBJECT-TYPE
    SYNTAX       CfprEquipmentRackUnitPsuStatsHistThresholded
    MAX-ACCESS   read-only
    STATUS       current
    DESCRIPTION
        "Cisco Firepower equipment:RackUnitPsuStatsHist:thresholded
        managed object property"
    ::= { cfprEquipmentRackUnitPsuStatsHistEntry 31 }

cfprEquipmentRackUnitPsuStatsHistTimeCollected OBJECT-TYPE
    SYNTAX       DateAndTime
    MAX-ACCESS   read-only
    STATUS       current
    DESCRIPTION
        "Cisco Firepower equipment:RackUnitPsuStatsHist:timeCollected
        managed object property"
    ::= { cfprEquipmentRackUnitPsuStatsHistEntry 32 }

cfprEquipmentRaidDefTable OBJECT-TYPE
    SYNTAX           SEQUENCE OF CfprEquipmentRaidDefEntry
    MAX-ACCESS       not-accessible
    STATUS           current
    DESCRIPTION
        "Cisco Firepower equipment:RaidDef managed object table"
    ::= { cfprEquipmentObjects 124 }

cfprEquipmentRaidDefEntry OBJECT-TYPE
    SYNTAX           CfprEquipmentRaidDefEntry
    MAX-ACCESS       not-accessible
    STATUS           current
    DESCRIPTION
        "Entry for the cfprEquipmentRaidDefTable table."
    INDEX { cfprEquipmentRaidDefInstanceId }
    ::= { cfprEquipmentRaidDefTable 1 }

CfprEquipmentRaidDefEntry ::= SEQUENCE {
    cfprEquipmentRaidDefInstanceId                                   CfprManagedObjectId,
    cfprEquipmentRaidDefDn                                           CfprManagedObjectDn,
    cfprEquipmentRaidDefRn                                           SnmpAdminString,
    cfprEquipmentRaidDefDescr                                        SnmpAdminString,
    cfprEquipmentRaidDefIntId                                        SnmpAdminString,
    cfprEquipmentRaidDefLevel                                        CfprStorageLocalDiskMode,
    cfprEquipmentRaidDefName                                         SnmpAdminString,
    cfprEquipmentRaidDefPolicyLevel                                  Gauge32,
    cfprEquipmentRaidDefPolicyOwner                                  CfprPolicyPolicyOwner
}

cfprEquipmentRaidDefInstanceId OBJECT-TYPE
    SYNTAX       CfprManagedObjectId
    MAX-ACCESS   not-accessible
    STATUS       current
    DESCRIPTION
        "Instance identifier of the managed object."
    ::= { cfprEquipmentRaidDefEntry 1 }

cfprEquipmentRaidDefDn OBJECT-TYPE
    SYNTAX       CfprManagedObjectDn
    MAX-ACCESS   read-only
    STATUS       current
    DESCRIPTION
        "Cisco Firepower equipment:RaidDef:dn managed object property"
    ::= { cfprEquipmentRaidDefEntry 2 }

cfprEquipmentRaidDefRn OBJECT-TYPE
    SYNTAX       SnmpAdminString
    MAX-ACCESS   read-only
    STATUS       current
    DESCRIPTION
        "Cisco Firepower equipment:RaidDef:rn managed object property"
    ::= { cfprEquipmentRaidDefEntry 3 }

cfprEquipmentRaidDefDescr OBJECT-TYPE
    SYNTAX       SnmpAdminString
    MAX-ACCESS   read-only
    STATUS       current
    DESCRIPTION
        "Cisco Firepower equipment:RaidDef:descr managed object property"
    ::= { cfprEquipmentRaidDefEntry 4 }

cfprEquipmentRaidDefIntId OBJECT-TYPE
    SYNTAX       SnmpAdminString
    MAX-ACCESS   read-only
    STATUS       current
    DESCRIPTION
        "Cisco Firepower equipment:RaidDef:intId managed object property"
    ::= { cfprEquipmentRaidDefEntry 5 }

cfprEquipmentRaidDefLevel OBJECT-TYPE
    SYNTAX       CfprStorageLocalDiskMode
    MAX-ACCESS   read-only
    STATUS       current
    DESCRIPTION
        "Cisco Firepower equipment:RaidDef:level managed object property"
    ::= { cfprEquipmentRaidDefEntry 6 }

cfprEquipmentRaidDefName OBJECT-TYPE
    SYNTAX       SnmpAdminString
    MAX-ACCESS   read-only
    STATUS       current
    DESCRIPTION
        "Cisco Firepower equipment:RaidDef:name managed object property"
    ::= { cfprEquipmentRaidDefEntry 7 }

cfprEquipmentRaidDefPolicyLevel OBJECT-TYPE
    SYNTAX       Gauge32
    MAX-ACCESS   read-only
    STATUS       current
    DESCRIPTION
        "Cisco Firepower equipment:RaidDef:policyLevel
        managed object property"
    ::= { cfprEquipmentRaidDefEntry 8 }

cfprEquipmentRaidDefPolicyOwner OBJECT-TYPE
    SYNTAX       CfprPolicyPolicyOwner
    MAX-ACCESS   read-only
    STATUS       current
    DESCRIPTION
        "Cisco Firepower equipment:RaidDef:policyOwner
        managed object property"
    ::= { cfprEquipmentRaidDefEntry 9 }

cfprEquipmentRommonTable OBJECT-TYPE
    SYNTAX           SEQUENCE OF CfprEquipmentRommonEntry
    MAX-ACCESS       not-accessible
    STATUS           current
    DESCRIPTION
        "Cisco Firepower equipment:Rommon managed object table"
    ::= { cfprEquipmentObjects 158 }

cfprEquipmentRommonEntry OBJECT-TYPE
    SYNTAX           CfprEquipmentRommonEntry
    MAX-ACCESS       not-accessible
    STATUS           current
    DESCRIPTION
        "Entry for the cfprEquipmentRommonTable table."
    INDEX { cfprEquipmentRommonInstanceId }
    ::= { cfprEquipmentRommonTable 1 }

CfprEquipmentRommonEntry ::= SEQUENCE {
    cfprEquipmentRommonInstanceId                                    CfprManagedObjectId,
    cfprEquipmentRommonDn                                            CfprManagedObjectDn,
    cfprEquipmentRommonRn                                            SnmpAdminString,
    cfprEquipmentRommonBkupPackageVersion                            SnmpAdminString,
    cfprEquipmentRommonBkupVersion                                   SnmpAdminString,
    cfprEquipmentRommonFltAggr                                       Unsigned64,
    cfprEquipmentRommonIsUpgradable                                  TruthValue,
    cfprEquipmentRommonModel                                         SnmpAdminString,
    cfprEquipmentRommonRevision                                      SnmpAdminString,
    cfprEquipmentRommonSerial                                        SnmpAdminString,
    cfprEquipmentRommonUpgradeStatus                                 SnmpAdminString,
    cfprEquipmentRommonVendor                                        SnmpAdminString
}

cfprEquipmentRommonInstanceId OBJECT-TYPE
    SYNTAX       CfprManagedObjectId
    MAX-ACCESS   not-accessible
    STATUS       current
    DESCRIPTION
        "Instance identifier of the managed object."
    ::= { cfprEquipmentRommonEntry 1 }

cfprEquipmentRommonDn OBJECT-TYPE
    SYNTAX       CfprManagedObjectDn
    MAX-ACCESS   read-only
    STATUS       current
    DESCRIPTION
        "Cisco Firepower equipment:Rommon:dn managed object property"
    ::= { cfprEquipmentRommonEntry 2 }

cfprEquipmentRommonRn OBJECT-TYPE
    SYNTAX       SnmpAdminString
    MAX-ACCESS   read-only
    STATUS       current
    DESCRIPTION
        "Cisco Firepower equipment:Rommon:rn managed object property"
    ::= { cfprEquipmentRommonEntry 3 }

cfprEquipmentRommonBkupPackageVersion OBJECT-TYPE
    SYNTAX       SnmpAdminString
    MAX-ACCESS   read-only
    STATUS       current
    DESCRIPTION
        "Cisco Firepower equipment:Rommon:bkupPackageVersion
        managed object property"
    ::= { cfprEquipmentRommonEntry 4 }

cfprEquipmentRommonBkupVersion OBJECT-TYPE
    SYNTAX       SnmpAdminString
    MAX-ACCESS   read-only
    STATUS       current
    DESCRIPTION
        "Cisco Firepower equipment:Rommon:bkupVersion managed
        object property"
    ::= { cfprEquipmentRommonEntry 5 }

cfprEquipmentRommonFltAggr OBJECT-TYPE
    SYNTAX       Unsigned64
    MAX-ACCESS   read-only
    STATUS       current
    DESCRIPTION
        "Cisco Firepower equipment:Rommon:fltAggr managed object property"
    ::= { cfprEquipmentRommonEntry 6 }

cfprEquipmentRommonIsUpgradable OBJECT-TYPE
    SYNTAX       TruthValue
    MAX-ACCESS   read-only
    STATUS       current
    DESCRIPTION
        "Cisco Firepower equipment:Rommon:isUpgradable
        managed object property"
    ::= { cfprEquipmentRommonEntry 7 }

cfprEquipmentRommonModel OBJECT-TYPE
    SYNTAX       SnmpAdminString
    MAX-ACCESS   read-only
    STATUS       current
    DESCRIPTION
        "Cisco Firepower equipment:Rommon:model managed object property"
    ::= { cfprEquipmentRommonEntry 8 }

cfprEquipmentRommonRevision OBJECT-TYPE
    SYNTAX       SnmpAdminString
    MAX-ACCESS   read-only
    STATUS       current
    DESCRIPTION
        "Cisco Firepower equipment:Rommon:revision managed
        object property"
    ::= { cfprEquipmentRommonEntry 9 }

cfprEquipmentRommonSerial OBJECT-TYPE
    SYNTAX       SnmpAdminString
    MAX-ACCESS   read-only
    STATUS       current
    DESCRIPTION
        "Cisco Firepower equipment:Rommon:serial managed object property"
    ::= { cfprEquipmentRommonEntry 10 }

cfprEquipmentRommonUpgradeStatus OBJECT-TYPE
    SYNTAX       SnmpAdminString
    MAX-ACCESS   read-only
    STATUS       current
    DESCRIPTION
        "Cisco Firepower equipment:Rommon:upgradeStatus
        managed object property"
    ::= { cfprEquipmentRommonEntry 11 }

cfprEquipmentRommonVendor OBJECT-TYPE
    SYNTAX       SnmpAdminString
    MAX-ACCESS   read-only
    STATUS       current
    DESCRIPTION
        "Cisco Firepower equipment:Rommon:vendor managed object property"
    ::= { cfprEquipmentRommonEntry 12 }

cfprEquipmentSecureBootTable OBJECT-TYPE
    SYNTAX           SEQUENCE OF CfprEquipmentSecureBootEntry
    MAX-ACCESS       not-accessible
    STATUS           current
    DESCRIPTION
        "Cisco Firepower equipment:SecureBoot managed object table"
    ::= { cfprEquipmentObjects 125 }

cfprEquipmentSecureBootEntry OBJECT-TYPE
    SYNTAX           CfprEquipmentSecureBootEntry
    MAX-ACCESS       not-accessible
    STATUS           current
    DESCRIPTION
        "Entry for the cfprEquipmentSecureBootTable table."
    INDEX { cfprEquipmentSecureBootInstanceId }
    ::= { cfprEquipmentSecureBootTable 1 }

CfprEquipmentSecureBootEntry ::= SEQUENCE {
    cfprEquipmentSecureBootInstanceId                                CfprManagedObjectId,
    cfprEquipmentSecureBootDn                                        CfprManagedObjectDn,
    cfprEquipmentSecureBootRn                                        SnmpAdminString,
    cfprEquipmentSecureBootDescr                                     SnmpAdminString,
    cfprEquipmentSecureBootIntId                                     SnmpAdminString,
    cfprEquipmentSecureBootMinBiosVersion                            SnmpAdminString,
    cfprEquipmentSecureBootMinCimcVersion                            SnmpAdminString,
    cfprEquipmentSecureBootName                                      SnmpAdminString,
    cfprEquipmentSecureBootPolicyLevel                               Gauge32,
    cfprEquipmentSecureBootPolicyOwner                               CfprPolicyPolicyOwner
}

cfprEquipmentSecureBootInstanceId OBJECT-TYPE
    SYNTAX       CfprManagedObjectId
    MAX-ACCESS   not-accessible
    STATUS       current
    DESCRIPTION
        "Instance identifier of the managed object."
    ::= { cfprEquipmentSecureBootEntry 1 }

cfprEquipmentSecureBootDn OBJECT-TYPE
    SYNTAX       CfprManagedObjectDn
    MAX-ACCESS   read-only
    STATUS       current
    DESCRIPTION
        "Cisco Firepower equipment:SecureBoot:dn managed object property"
    ::= { cfprEquipmentSecureBootEntry 2 }

cfprEquipmentSecureBootRn OBJECT-TYPE
    SYNTAX       SnmpAdminString
    MAX-ACCESS   read-only
    STATUS       current
    DESCRIPTION
        "Cisco Firepower equipment:SecureBoot:rn managed object property"
    ::= { cfprEquipmentSecureBootEntry 3 }

cfprEquipmentSecureBootDescr OBJECT-TYPE
    SYNTAX       SnmpAdminString
    MAX-ACCESS   read-only
    STATUS       current
    DESCRIPTION
        "Cisco Firepower equipment:SecureBoot:descr managed
        object property"
    ::= { cfprEquipmentSecureBootEntry 4 }

cfprEquipmentSecureBootIntId OBJECT-TYPE
    SYNTAX       SnmpAdminString
    MAX-ACCESS   read-only
    STATUS       current
    DESCRIPTION
        "Cisco Firepower equipment:SecureBoot:intId managed
        object property"
    ::= { cfprEquipmentSecureBootEntry 5 }

cfprEquipmentSecureBootMinBiosVersion OBJECT-TYPE
    SYNTAX       SnmpAdminString
    MAX-ACCESS   read-only
    STATUS       current
    DESCRIPTION
        "Cisco Firepower equipment:SecureBoot:minBiosVersion
        managed object property"
    ::= { cfprEquipmentSecureBootEntry 6 }

cfprEquipmentSecureBootMinCimcVersion OBJECT-TYPE
    SYNTAX       SnmpAdminString
    MAX-ACCESS   read-only
    STATUS       current
    DESCRIPTION
        "Cisco Firepower equipment:SecureBoot:minCimcVersion
        managed object property"
    ::= { cfprEquipmentSecureBootEntry 7 }

cfprEquipmentSecureBootName OBJECT-TYPE
    SYNTAX       SnmpAdminString
    MAX-ACCESS   read-only
    STATUS       current
    DESCRIPTION
        "Cisco Firepower equipment:SecureBoot:name managed
        object property"
    ::= { cfprEquipmentSecureBootEntry 8 }

cfprEquipmentSecureBootPolicyLevel OBJECT-TYPE
    SYNTAX       Gauge32
    MAX-ACCESS   read-only
    STATUS       current
    DESCRIPTION
        "Cisco Firepower equipment:SecureBoot:policyLevel
        managed object property"
    ::= { cfprEquipmentSecureBootEntry 9 }

cfprEquipmentSecureBootPolicyOwner OBJECT-TYPE
    SYNTAX       CfprPolicyPolicyOwner
    MAX-ACCESS   read-only
    STATUS       current
    DESCRIPTION
        "Cisco Firepower equipment:SecureBoot:policyOwner
        managed object property"
    ::= { cfprEquipmentSecureBootEntry 10 }

cfprEquipmentServerFeatureCapTable OBJECT-TYPE
    SYNTAX           SEQUENCE OF CfprEquipmentServerFeatureCapEntry
    MAX-ACCESS       not-accessible
    STATUS           current
    DESCRIPTION
        "Cisco Firepower equipment:ServerFeatureCap managed object table"
    ::= { cfprEquipmentObjects 126 }

cfprEquipmentServerFeatureCapEntry OBJECT-TYPE
    SYNTAX           CfprEquipmentServerFeatureCapEntry
    MAX-ACCESS       not-accessible
    STATUS           current
    DESCRIPTION
        "Entry for the cfprEquipmentServerFeatureCapTable table."
    INDEX { cfprEquipmentServerFeatureCapInstanceId }
    ::= { cfprEquipmentServerFeatureCapTable 1 }

CfprEquipmentServerFeatureCapEntry ::= SEQUENCE {
    cfprEquipmentServerFeatureCapInstanceId                          CfprManagedObjectId,
    cfprEquipmentServerFeatureCapDn                                  CfprManagedObjectDn,
    cfprEquipmentServerFeatureCapRn                                  SnmpAdminString,
    cfprEquipmentServerFeatureCapCmosResetSupported                  TruthValue
}

cfprEquipmentServerFeatureCapInstanceId OBJECT-TYPE
    SYNTAX       CfprManagedObjectId
    MAX-ACCESS   not-accessible
    STATUS       current
    DESCRIPTION
        "Instance identifier of the managed object."
    ::= { cfprEquipmentServerFeatureCapEntry 1 }

cfprEquipmentServerFeatureCapDn OBJECT-TYPE
    SYNTAX       CfprManagedObjectDn
    MAX-ACCESS   read-only
    STATUS       current
    DESCRIPTION
        "Cisco Firepower equipment:ServerFeatureCap:dn
        managed object property"
    ::= { cfprEquipmentServerFeatureCapEntry 2 }

cfprEquipmentServerFeatureCapRn OBJECT-TYPE
    SYNTAX       SnmpAdminString
    MAX-ACCESS   read-only
    STATUS       current
    DESCRIPTION
        "Cisco Firepower equipment:ServerFeatureCap:rn
        managed object property"
    ::= { cfprEquipmentServerFeatureCapEntry 3 }

cfprEquipmentServerFeatureCapCmosResetSupported OBJECT-TYPE
    SYNTAX       TruthValue
    MAX-ACCESS   read-only
    STATUS       current
    DESCRIPTION
        "Cisco Firepower equipment:ServerFeatureCap:cmosResetSupported
        managed object property"
    ::= { cfprEquipmentServerFeatureCapEntry 4 }

cfprEquipmentServerPortCapProviderTable OBJECT-TYPE
    SYNTAX           SEQUENCE OF CfprEquipmentServerPortCapProviderEntry
    MAX-ACCESS       not-accessible
    STATUS           current
    DESCRIPTION
        "Cisco Firepower equipment:ServerPortCapProvider
        managed object table"
    ::= { cfprEquipmentObjects 127 }

cfprEquipmentServerPortCapProviderEntry OBJECT-TYPE
    SYNTAX           CfprEquipmentServerPortCapProviderEntry
    MAX-ACCESS       not-accessible
    STATUS           current
    DESCRIPTION
        "Entry for the cfprEquipmentServerPortCapProviderTable table."
    INDEX { cfprEquipmentServerPortCapProviderInstanceId }
    ::= { cfprEquipmentServerPortCapProviderTable 1 }

CfprEquipmentServerPortCapProviderEntry ::= SEQUENCE {
    cfprEquipmentServerPortCapProviderInstanceId                     CfprManagedObjectId,
    cfprEquipmentServerPortCapProviderDn                             CfprManagedObjectDn,
    cfprEquipmentServerPortCapProviderRn                             SnmpAdminString,
    cfprEquipmentServerPortCapProviderDescr                          SnmpAdminString,
    cfprEquipmentServerPortCapProviderEndPortId                      Gauge32,
    cfprEquipmentServerPortCapProviderIntId                          SnmpAdminString,
    cfprEquipmentServerPortCapProviderName                           SnmpAdminString,
    cfprEquipmentServerPortCapProviderPolicyLevel                    Gauge32,
    cfprEquipmentServerPortCapProviderPolicyOwner                    CfprPolicyPolicyOwner,
    cfprEquipmentServerPortCapProviderStartPortId                    Gauge32
}

cfprEquipmentServerPortCapProviderInstanceId OBJECT-TYPE
    SYNTAX       CfprManagedObjectId
    MAX-ACCESS   not-accessible
    STATUS       current
    DESCRIPTION
        "Instance identifier of the managed object."
    ::= { cfprEquipmentServerPortCapProviderEntry 1 }

cfprEquipmentServerPortCapProviderDn OBJECT-TYPE
    SYNTAX       CfprManagedObjectDn
    MAX-ACCESS   read-only
    STATUS       current
    DESCRIPTION
        "Cisco Firepower equipment:ServerPortCapProvider:dn
        managed object property"
    ::= { cfprEquipmentServerPortCapProviderEntry 2 }

cfprEquipmentServerPortCapProviderRn OBJECT-TYPE
    SYNTAX       SnmpAdminString
    MAX-ACCESS   read-only
    STATUS       current
    DESCRIPTION
        "Cisco Firepower equipment:ServerPortCapProvider:rn
        managed object property"
    ::= { cfprEquipmentServerPortCapProviderEntry 3 }

cfprEquipmentServerPortCapProviderDescr OBJECT-TYPE
    SYNTAX       SnmpAdminString
    MAX-ACCESS   read-only
    STATUS       current
    DESCRIPTION
        "Cisco Firepower equipment:ServerPortCapProvider:descr
        managed object property"
    ::= { cfprEquipmentServerPortCapProviderEntry 4 }

cfprEquipmentServerPortCapProviderEndPortId OBJECT-TYPE
    SYNTAX       Gauge32
    MAX-ACCESS   read-only
    STATUS       current
    DESCRIPTION
        "Cisco Firepower equipment:ServerPortCapProvider:endPortId
        managed object property"
    ::= { cfprEquipmentServerPortCapProviderEntry 5 }

cfprEquipmentServerPortCapProviderIntId OBJECT-TYPE
    SYNTAX       SnmpAdminString
    MAX-ACCESS   read-only
    STATUS       current
    DESCRIPTION
        "Cisco Firepower equipment:ServerPortCapProvider:intId
        managed object property"
    ::= { cfprEquipmentServerPortCapProviderEntry 6 }

cfprEquipmentServerPortCapProviderName OBJECT-TYPE
    SYNTAX       SnmpAdminString
    MAX-ACCESS   read-only
    STATUS       current
    DESCRIPTION
        "Cisco Firepower equipment:ServerPortCapProvider:name
        managed object property"
    ::= { cfprEquipmentServerPortCapProviderEntry 7 }

cfprEquipmentServerPortCapProviderPolicyLevel OBJECT-TYPE
    SYNTAX       Gauge32
    MAX-ACCESS   read-only
    STATUS       current
    DESCRIPTION
        "Cisco Firepower equipment:ServerPortCapProvider:policyLevel
        managed object property"
    ::= { cfprEquipmentServerPortCapProviderEntry 8 }

cfprEquipmentServerPortCapProviderPolicyOwner OBJECT-TYPE
    SYNTAX       CfprPolicyPolicyOwner
    MAX-ACCESS   read-only
    STATUS       current
    DESCRIPTION
        "Cisco Firepower equipment:ServerPortCapProvider:policyOwner
        managed object property"
    ::= { cfprEquipmentServerPortCapProviderEntry 9 }

cfprEquipmentServerPortCapProviderStartPortId OBJECT-TYPE
    SYNTAX       Gauge32
    MAX-ACCESS   read-only
    STATUS       current
    DESCRIPTION
        "Cisco Firepower equipment:ServerPortCapProvider:startPortId
        managed object property"
    ::= { cfprEquipmentServerPortCapProviderEntry 10 }

cfprEquipmentServiceDefTable OBJECT-TYPE
    SYNTAX           SEQUENCE OF CfprEquipmentServiceDefEntry
    MAX-ACCESS       not-accessible
    STATUS           current
    DESCRIPTION
        "Cisco Firepower equipment:ServiceDef managed object table"
    ::= { cfprEquipmentObjects 128 }

cfprEquipmentServiceDefEntry OBJECT-TYPE
    SYNTAX           CfprEquipmentServiceDefEntry
    MAX-ACCESS       not-accessible
    STATUS           current
    DESCRIPTION
        "Entry for the cfprEquipmentServiceDefTable table."
    INDEX { cfprEquipmentServiceDefInstanceId }
    ::= { cfprEquipmentServiceDefTable 1 }

CfprEquipmentServiceDefEntry ::= SEQUENCE {
    cfprEquipmentServiceDefInstanceId                                CfprManagedObjectId,
    cfprEquipmentServiceDefDn                                        CfprManagedObjectDn,
    cfprEquipmentServiceDefRn                                        SnmpAdminString,
    cfprEquipmentServiceDefCanBeFRUed                                TruthValue,
    cfprEquipmentServiceDefDescr                                     SnmpAdminString,
    cfprEquipmentServiceDefIntId                                     SnmpAdminString,
    cfprEquipmentServiceDefName                                      SnmpAdminString,
    cfprEquipmentServiceDefPolicyLevel                               Gauge32,
    cfprEquipmentServiceDefPolicyOwner                               CfprPolicyPolicyOwner,
    cfprEquipmentServiceDefRemovalConditions                         CfprEquipmentRemovalConditions,
    cfprEquipmentServiceDefServicePhilosophy                         SnmpAdminString
}

cfprEquipmentServiceDefInstanceId OBJECT-TYPE
    SYNTAX       CfprManagedObjectId
    MAX-ACCESS   not-accessible
    STATUS       current
    DESCRIPTION
        "Instance identifier of the managed object."
    ::= { cfprEquipmentServiceDefEntry 1 }

cfprEquipmentServiceDefDn OBJECT-TYPE
    SYNTAX       CfprManagedObjectDn
    MAX-ACCESS   read-only
    STATUS       current
    DESCRIPTION
        "Cisco Firepower equipment:ServiceDef:dn managed object property"
    ::= { cfprEquipmentServiceDefEntry 2 }

cfprEquipmentServiceDefRn OBJECT-TYPE
    SYNTAX       SnmpAdminString
    MAX-ACCESS   read-only
    STATUS       current
    DESCRIPTION
        "Cisco Firepower equipment:ServiceDef:rn managed object property"
    ::= { cfprEquipmentServiceDefEntry 3 }

cfprEquipmentServiceDefCanBeFRUed OBJECT-TYPE
    SYNTAX       TruthValue
    MAX-ACCESS   read-only
    STATUS       current
    DESCRIPTION
        "Cisco Firepower equipment:ServiceDef:canBeFRUed
        managed object property"
    ::= { cfprEquipmentServiceDefEntry 4 }

cfprEquipmentServiceDefDescr OBJECT-TYPE
    SYNTAX       SnmpAdminString
    MAX-ACCESS   read-only
    STATUS       current
    DESCRIPTION
        "Cisco Firepower equipment:ServiceDef:descr managed
        object property"
    ::= { cfprEquipmentServiceDefEntry 5 }

cfprEquipmentServiceDefIntId OBJECT-TYPE
    SYNTAX       SnmpAdminString
    MAX-ACCESS   read-only
    STATUS       current
    DESCRIPTION
        "Cisco Firepower equipment:ServiceDef:intId managed
        object property"
    ::= { cfprEquipmentServiceDefEntry 6 }

cfprEquipmentServiceDefName OBJECT-TYPE
    SYNTAX       SnmpAdminString
    MAX-ACCESS   read-only
    STATUS       current
    DESCRIPTION
        "Cisco Firepower equipment:ServiceDef:name managed
        object property"
    ::= { cfprEquipmentServiceDefEntry 7 }

cfprEquipmentServiceDefPolicyLevel OBJECT-TYPE
    SYNTAX       Gauge32
    MAX-ACCESS   read-only
    STATUS       current
    DESCRIPTION
        "Cisco Firepower equipment:ServiceDef:policyLevel
        managed object property"
    ::= { cfprEquipmentServiceDefEntry 8 }

cfprEquipmentServiceDefPolicyOwner OBJECT-TYPE
    SYNTAX       CfprPolicyPolicyOwner
    MAX-ACCESS   read-only
    STATUS       current
    DESCRIPTION
        "Cisco Firepower equipment:ServiceDef:policyOwner
        managed object property"
    ::= { cfprEquipmentServiceDefEntry 9 }

cfprEquipmentServiceDefRemovalConditions OBJECT-TYPE
    SYNTAX       CfprEquipmentRemovalConditions
    MAX-ACCESS   read-only
    STATUS       current
    DESCRIPTION
        "Cisco Firepower equipment:ServiceDef:removalConditions
        managed object property"
    ::= { cfprEquipmentServiceDefEntry 10 }

cfprEquipmentServiceDefServicePhilosophy OBJECT-TYPE
    SYNTAX       SnmpAdminString
    MAX-ACCESS   read-only
    STATUS       current
    DESCRIPTION
        "Cisco Firepower equipment:ServiceDef:servicePhilosophy
        managed object property"
    ::= { cfprEquipmentServiceDefEntry 11 }

cfprEquipmentSlotArrayTable OBJECT-TYPE
    SYNTAX           SEQUENCE OF CfprEquipmentSlotArrayEntry
    MAX-ACCESS       not-accessible
    STATUS           current
    DESCRIPTION
        "Cisco Firepower equipment:SlotArray managed object table"
    ::= { cfprEquipmentObjects 129 }

cfprEquipmentSlotArrayEntry OBJECT-TYPE
    SYNTAX           CfprEquipmentSlotArrayEntry
    MAX-ACCESS       not-accessible
    STATUS           current
    DESCRIPTION
        "Entry for the cfprEquipmentSlotArrayTable table."
    INDEX { cfprEquipmentSlotArrayInstanceId }
    ::= { cfprEquipmentSlotArrayTable 1 }

CfprEquipmentSlotArrayEntry ::= SEQUENCE {
    cfprEquipmentSlotArrayInstanceId                                 CfprManagedObjectId,
    cfprEquipmentSlotArrayDn                                         CfprManagedObjectDn,
    cfprEquipmentSlotArrayRn                                         SnmpAdminString,
    cfprEquipmentSlotArrayDescr                                      SnmpAdminString,
    cfprEquipmentSlotArrayFirstIndex                                 Gauge32,
    cfprEquipmentSlotArrayHeight                                     INTEGER,
    cfprEquipmentSlotArrayHorizontalStartOffset                      INTEGER,
    cfprEquipmentSlotArrayInlineGroupSeparation                      INTEGER,
    cfprEquipmentSlotArrayInlineGroupSize                            Gauge32,
    cfprEquipmentSlotArrayInlineOffset                               INTEGER,
    cfprEquipmentSlotArrayIntId                                      SnmpAdminString,
    cfprEquipmentSlotArrayLocation                                   CfprEquipmentSlotArrayLocation,
    cfprEquipmentSlotArrayName                                       SnmpAdminString,
    cfprEquipmentSlotArrayNumberOfSlots                              Gauge32,
    cfprEquipmentSlotArrayOrientation                                CfprEquipmentSlotArrayOrientation,
    cfprEquipmentSlotArrayPolicyLevel                                Gauge32,
    cfprEquipmentSlotArrayPolicyOwner                                CfprPolicyPolicyOwner,
    cfprEquipmentSlotArraySelector                                   CfprEquipmentSlotArraySelector,
    cfprEquipmentSlotArraySlotsPerLine                               Gauge32,
    cfprEquipmentSlotArrayTransverseGroupSeparation                  INTEGER,
    cfprEquipmentSlotArrayTransverseGroupSize                        Gauge32,
    cfprEquipmentSlotArrayTransverseOffset                           INTEGER,
    cfprEquipmentSlotArrayVerticalStartOffset                        INTEGER,
    cfprEquipmentSlotArrayWidth                                      INTEGER
}

cfprEquipmentSlotArrayInstanceId OBJECT-TYPE
    SYNTAX       CfprManagedObjectId
    MAX-ACCESS   not-accessible
    STATUS       current
    DESCRIPTION
        "Instance identifier of the managed object."
    ::= { cfprEquipmentSlotArrayEntry 1 }

cfprEquipmentSlotArrayDn OBJECT-TYPE
    SYNTAX       CfprManagedObjectDn
    MAX-ACCESS   read-only
    STATUS       current
    DESCRIPTION
        "Cisco Firepower equipment:SlotArray:dn managed object property"
    ::= { cfprEquipmentSlotArrayEntry 2 }

cfprEquipmentSlotArrayRn OBJECT-TYPE
    SYNTAX       SnmpAdminString
    MAX-ACCESS   read-only
    STATUS       current
    DESCRIPTION
        "Cisco Firepower equipment:SlotArray:rn managed object property"
    ::= { cfprEquipmentSlotArrayEntry 3 }

cfprEquipmentSlotArrayDescr OBJECT-TYPE
    SYNTAX       SnmpAdminString
    MAX-ACCESS   read-only
    STATUS       current
    DESCRIPTION
        "Cisco Firepower equipment:SlotArray:descr managed
        object property"
    ::= { cfprEquipmentSlotArrayEntry 4 }

cfprEquipmentSlotArrayFirstIndex OBJECT-TYPE
    SYNTAX       Gauge32
    MAX-ACCESS   read-only
    STATUS       current
    DESCRIPTION
        "Cisco Firepower equipment:SlotArray:firstIndex
        managed object property"
    ::= { cfprEquipmentSlotArrayEntry 5 }

cfprEquipmentSlotArrayHeight OBJECT-TYPE
    SYNTAX       INTEGER
    MAX-ACCESS   read-only
    STATUS       current
    DESCRIPTION
        "Cisco Firepower equipment:SlotArray:height managed
        object property"
    ::= { cfprEquipmentSlotArrayEntry 6 }

cfprEquipmentSlotArrayHorizontalStartOffset OBJECT-TYPE
    SYNTAX       INTEGER
    MAX-ACCESS   read-only
    STATUS       current
    DESCRIPTION
        "Cisco Firepower equipment:SlotArray:horizontalStartOffset
        managed object property"
    ::= { cfprEquipmentSlotArrayEntry 7 }

cfprEquipmentSlotArrayInlineGroupSeparation OBJECT-TYPE
    SYNTAX       INTEGER
    MAX-ACCESS   read-only
    STATUS       current
    DESCRIPTION
        "Cisco Firepower equipment:SlotArray:inlineGroupSeparation
        managed object property"
    ::= { cfprEquipmentSlotArrayEntry 8 }

cfprEquipmentSlotArrayInlineGroupSize OBJECT-TYPE
    SYNTAX       Gauge32
    MAX-ACCESS   read-only
    STATUS       current
    DESCRIPTION
        "Cisco Firepower equipment:SlotArray:inlineGroupSize
        managed object property"
    ::= { cfprEquipmentSlotArrayEntry 9 }

cfprEquipmentSlotArrayInlineOffset OBJECT-TYPE
    SYNTAX       INTEGER
    MAX-ACCESS   read-only
    STATUS       current
    DESCRIPTION
        "Cisco Firepower equipment:SlotArray:inlineOffset
        managed object property"
    ::= { cfprEquipmentSlotArrayEntry 10 }

cfprEquipmentSlotArrayIntId OBJECT-TYPE
    SYNTAX       SnmpAdminString
    MAX-ACCESS   read-only
    STATUS       current
    DESCRIPTION
        "Cisco Firepower equipment:SlotArray:intId managed
        object property"
    ::= { cfprEquipmentSlotArrayEntry 11 }

cfprEquipmentSlotArrayLocation OBJECT-TYPE
    SYNTAX       CfprEquipmentSlotArrayLocation
    MAX-ACCESS   read-only
    STATUS       current
    DESCRIPTION
        "Cisco Firepower equipment:SlotArray:location managed
        object property"
    ::= { cfprEquipmentSlotArrayEntry 12 }

cfprEquipmentSlotArrayName OBJECT-TYPE
    SYNTAX       SnmpAdminString
    MAX-ACCESS   read-only
    STATUS       current
    DESCRIPTION
        "Cisco Firepower equipment:SlotArray:name managed object property"
    ::= { cfprEquipmentSlotArrayEntry 13 }

cfprEquipmentSlotArrayNumberOfSlots OBJECT-TYPE
    SYNTAX       Gauge32
    MAX-ACCESS   read-only
    STATUS       current
    DESCRIPTION
        "Cisco Firepower equipment:SlotArray:numberOfSlots
        managed object property"
    ::= { cfprEquipmentSlotArrayEntry 14 }

cfprEquipmentSlotArrayOrientation OBJECT-TYPE
    SYNTAX       CfprEquipmentSlotArrayOrientation
    MAX-ACCESS   read-only
    STATUS       current
    DESCRIPTION
        "Cisco Firepower equipment:SlotArray:orientation
        managed object property"
    ::= { cfprEquipmentSlotArrayEntry 15 }

cfprEquipmentSlotArrayPolicyLevel OBJECT-TYPE
    SYNTAX       Gauge32
    MAX-ACCESS   read-only
    STATUS       current
    DESCRIPTION
        "Cisco Firepower equipment:SlotArray:policyLevel
        managed object property"
    ::= { cfprEquipmentSlotArrayEntry 16 }

cfprEquipmentSlotArrayPolicyOwner OBJECT-TYPE
    SYNTAX       CfprPolicyPolicyOwner
    MAX-ACCESS   read-only
    STATUS       current
    DESCRIPTION
        "Cisco Firepower equipment:SlotArray:policyOwner
        managed object property"
    ::= { cfprEquipmentSlotArrayEntry 17 }

cfprEquipmentSlotArraySelector OBJECT-TYPE
    SYNTAX       CfprEquipmentSlotArraySelector
    MAX-ACCESS   read-only
    STATUS       current
    DESCRIPTION
        "Cisco Firepower equipment:SlotArray:selector managed
        object property"
    ::= { cfprEquipmentSlotArrayEntry 18 }

cfprEquipmentSlotArraySlotsPerLine OBJECT-TYPE
    SYNTAX       Gauge32
    MAX-ACCESS   read-only
    STATUS       current
    DESCRIPTION
        "Cisco Firepower equipment:SlotArray:slotsPerLine
        managed object property"
    ::= { cfprEquipmentSlotArrayEntry 19 }

cfprEquipmentSlotArrayTransverseGroupSeparation OBJECT-TYPE
    SYNTAX       INTEGER
    MAX-ACCESS   read-only
    STATUS       current
    DESCRIPTION
        "Cisco Firepower equipment:SlotArray:transverseGroupSeparation
        managed object property"
    ::= { cfprEquipmentSlotArrayEntry 20 }

cfprEquipmentSlotArrayTransverseGroupSize OBJECT-TYPE
    SYNTAX       Gauge32
    MAX-ACCESS   read-only
    STATUS       current
    DESCRIPTION
        "Cisco Firepower equipment:SlotArray:transverseGroupSize
        managed object property"
    ::= { cfprEquipmentSlotArrayEntry 21 }

cfprEquipmentSlotArrayTransverseOffset OBJECT-TYPE
    SYNTAX       INTEGER
    MAX-ACCESS   read-only
    STATUS       current
    DESCRIPTION
        "Cisco Firepower equipment:SlotArray:transverseOffset
        managed object property"
    ::= { cfprEquipmentSlotArrayEntry 22 }

cfprEquipmentSlotArrayVerticalStartOffset OBJECT-TYPE
    SYNTAX       INTEGER
    MAX-ACCESS   read-only
    STATUS       current
    DESCRIPTION
        "Cisco Firepower equipment:SlotArray:verticalStartOffset
        managed object property"
    ::= { cfprEquipmentSlotArrayEntry 23 }

cfprEquipmentSlotArrayWidth OBJECT-TYPE
    SYNTAX       INTEGER
    MAX-ACCESS   read-only
    STATUS       current
    DESCRIPTION
        "Cisco Firepower equipment:SlotArray:width managed
        object property"
    ::= { cfprEquipmentSlotArrayEntry 24 }

cfprEquipmentSlotArrayRefTable OBJECT-TYPE
    SYNTAX           SEQUENCE OF CfprEquipmentSlotArrayRefEntry
    MAX-ACCESS       not-accessible
    STATUS           current
    DESCRIPTION
        "Cisco Firepower equipment:SlotArrayRef managed object table"
    ::= { cfprEquipmentObjects 130 }

cfprEquipmentSlotArrayRefEntry OBJECT-TYPE
    SYNTAX           CfprEquipmentSlotArrayRefEntry
    MAX-ACCESS       not-accessible
    STATUS           current
    DESCRIPTION
        "Entry for the cfprEquipmentSlotArrayRefTable table."
    INDEX { cfprEquipmentSlotArrayRefInstanceId }
    ::= { cfprEquipmentSlotArrayRefTable 1 }

CfprEquipmentSlotArrayRefEntry ::= SEQUENCE {
    cfprEquipmentSlotArrayRefInstanceId                              CfprManagedObjectId,
    cfprEquipmentSlotArrayRefDn                                      CfprManagedObjectDn,
    cfprEquipmentSlotArrayRefRn                                      SnmpAdminString,
    cfprEquipmentSlotArrayRefDescr                                   SnmpAdminString,
    cfprEquipmentSlotArrayRefIntId                                   SnmpAdminString,
    cfprEquipmentSlotArrayRefName                                    SnmpAdminString,
    cfprEquipmentSlotArrayRefNumberOfSlotsSpanned                    Gauge32,
    cfprEquipmentSlotArrayRefPolicyLevel                             Gauge32,
    cfprEquipmentSlotArrayRefPolicyOwner                             CfprPolicyPolicyOwner,
    cfprEquipmentSlotArrayRefSlotSpanOrientation                     CfprEquipmentSlotSpanOrientation,
    cfprEquipmentSlotArrayRefTargetDn                                SnmpAdminString
}

cfprEquipmentSlotArrayRefInstanceId OBJECT-TYPE
    SYNTAX       CfprManagedObjectId
    MAX-ACCESS   not-accessible
    STATUS       current
    DESCRIPTION
        "Instance identifier of the managed object."
    ::= { cfprEquipmentSlotArrayRefEntry 1 }

cfprEquipmentSlotArrayRefDn OBJECT-TYPE
    SYNTAX       CfprManagedObjectDn
    MAX-ACCESS   read-only
    STATUS       current
    DESCRIPTION
        "Cisco Firepower equipment:SlotArrayRef:dn managed
        object property"
    ::= { cfprEquipmentSlotArrayRefEntry 2 }

cfprEquipmentSlotArrayRefRn OBJECT-TYPE
    SYNTAX       SnmpAdminString
    MAX-ACCESS   read-only
    STATUS       current
    DESCRIPTION
        "Cisco Firepower equipment:SlotArrayRef:rn managed
        object property"
    ::= { cfprEquipmentSlotArrayRefEntry 3 }

cfprEquipmentSlotArrayRefDescr OBJECT-TYPE
    SYNTAX       SnmpAdminString
    MAX-ACCESS   read-only
    STATUS       current
    DESCRIPTION
        "Cisco Firepower equipment:SlotArrayRef:descr managed
        object property"
    ::= { cfprEquipmentSlotArrayRefEntry 4 }

cfprEquipmentSlotArrayRefIntId OBJECT-TYPE
    SYNTAX       SnmpAdminString
    MAX-ACCESS   read-only
    STATUS       current
    DESCRIPTION
        "Cisco Firepower equipment:SlotArrayRef:intId managed
        object property"
    ::= { cfprEquipmentSlotArrayRefEntry 5 }

cfprEquipmentSlotArrayRefName OBJECT-TYPE
    SYNTAX       SnmpAdminString
    MAX-ACCESS   read-only
    STATUS       current
    DESCRIPTION
        "Cisco Firepower equipment:SlotArrayRef:name managed
        object property"
    ::= { cfprEquipmentSlotArrayRefEntry 6 }

cfprEquipmentSlotArrayRefNumberOfSlotsSpanned OBJECT-TYPE
    SYNTAX       Gauge32
    MAX-ACCESS   read-only
    STATUS       current
    DESCRIPTION
        "Cisco Firepower equipment:SlotArrayRef:numberOfSlotsSpanned
        managed object property"
    ::= { cfprEquipmentSlotArrayRefEntry 7 }

cfprEquipmentSlotArrayRefPolicyLevel OBJECT-TYPE
    SYNTAX       Gauge32
    MAX-ACCESS   read-only
    STATUS       current
    DESCRIPTION
        "Cisco Firepower equipment:SlotArrayRef:policyLevel
        managed object property"
    ::= { cfprEquipmentSlotArrayRefEntry 8 }

cfprEquipmentSlotArrayRefPolicyOwner OBJECT-TYPE
    SYNTAX       CfprPolicyPolicyOwner
    MAX-ACCESS   read-only
    STATUS       current
    DESCRIPTION
        "Cisco Firepower equipment:SlotArrayRef:policyOwner
        managed object property"
    ::= { cfprEquipmentSlotArrayRefEntry 9 }

cfprEquipmentSlotArrayRefSlotSpanOrientation OBJECT-TYPE
    SYNTAX       CfprEquipmentSlotSpanOrientation
    MAX-ACCESS   read-only
    STATUS       current
    DESCRIPTION
        "Cisco Firepower equipment:SlotArrayRef:slotSpanOrientation
        managed object property"
    ::= { cfprEquipmentSlotArrayRefEntry 10 }

cfprEquipmentSlotArrayRefTargetDn OBJECT-TYPE
    SYNTAX       SnmpAdminString
    MAX-ACCESS   read-only
    STATUS       current
    DESCRIPTION
        "Cisco Firepower equipment:SlotArrayRef:targetDn
        managed object property"
    ::= { cfprEquipmentSlotArrayRefEntry 11 }

cfprEquipmentSsdTable OBJECT-TYPE
    SYNTAX           SEQUENCE OF CfprEquipmentSsdEntry
    MAX-ACCESS       not-accessible
    STATUS           current
    DESCRIPTION
        "Cisco Firepower equipment:Ssd managed object table"
    ::= { cfprEquipmentObjects 159 }

cfprEquipmentSsdEntry OBJECT-TYPE
    SYNTAX           CfprEquipmentSsdEntry
    MAX-ACCESS       not-accessible
    STATUS           current
    DESCRIPTION
        "Entry for the cfprEquipmentSsdTable table."
    INDEX { cfprEquipmentSsdInstanceId }
    ::= { cfprEquipmentSsdTable 1 }

CfprEquipmentSsdEntry ::= SEQUENCE {
    cfprEquipmentSsdInstanceId                                       CfprManagedObjectId,
    cfprEquipmentSsdDn                                               CfprManagedObjectDn,
    cfprEquipmentSsdRn                                               SnmpAdminString,
    cfprEquipmentSsdBkupPackageVersion                               SnmpAdminString,
    cfprEquipmentSsdBkupVersion                                      SnmpAdminString,
    cfprEquipmentSsdFltAggr                                          Unsigned64,
    cfprEquipmentSsdIsUpgradable                                     TruthValue,
    cfprEquipmentSsdIsUpgradeRequired                                TruthValue,
    cfprEquipmentSsdModel                                            SnmpAdminString,
    cfprEquipmentSsdRevision                                         SnmpAdminString,
    cfprEquipmentSsdSerial                                           SnmpAdminString,
    cfprEquipmentSsdVendor                                           SnmpAdminString
}

cfprEquipmentSsdInstanceId OBJECT-TYPE
    SYNTAX       CfprManagedObjectId
    MAX-ACCESS   not-accessible
    STATUS       current
    DESCRIPTION
        "Instance identifier of the managed object."
    ::= { cfprEquipmentSsdEntry 1 }

cfprEquipmentSsdDn OBJECT-TYPE
    SYNTAX       CfprManagedObjectDn
    MAX-ACCESS   read-only
    STATUS       current
    DESCRIPTION
        "Cisco Firepower equipment:Ssd:dn managed object property"
    ::= { cfprEquipmentSsdEntry 2 }

cfprEquipmentSsdRn OBJECT-TYPE
    SYNTAX       SnmpAdminString
    MAX-ACCESS   read-only
    STATUS       current
    DESCRIPTION
        "Cisco Firepower equipment:Ssd:rn managed object property"
    ::= { cfprEquipmentSsdEntry 3 }

cfprEquipmentSsdBkupPackageVersion OBJECT-TYPE
    SYNTAX       SnmpAdminString
    MAX-ACCESS   read-only
    STATUS       current
    DESCRIPTION
        "Cisco Firepower equipment:Ssd:bkupPackageVersion
        managed object property"
    ::= { cfprEquipmentSsdEntry 4 }

cfprEquipmentSsdBkupVersion OBJECT-TYPE
    SYNTAX       SnmpAdminString
    MAX-ACCESS   read-only
    STATUS       current
    DESCRIPTION
        "Cisco Firepower equipment:Ssd:bkupVersion managed
        object property"
    ::= { cfprEquipmentSsdEntry 5 }

cfprEquipmentSsdFltAggr OBJECT-TYPE
    SYNTAX       Unsigned64
    MAX-ACCESS   read-only
    STATUS       current
    DESCRIPTION
        "Cisco Firepower equipment:Ssd:fltAggr managed object property"
    ::= { cfprEquipmentSsdEntry 6 }

cfprEquipmentSsdIsUpgradable OBJECT-TYPE
    SYNTAX       TruthValue
    MAX-ACCESS   read-only
    STATUS       current
    DESCRIPTION
        "Cisco Firepower equipment:Ssd:isUpgradable managed
        object property"
    ::= { cfprEquipmentSsdEntry 7 }

cfprEquipmentSsdIsUpgradeRequired OBJECT-TYPE
    SYNTAX       TruthValue
    MAX-ACCESS   read-only
    STATUS       current
    DESCRIPTION
        "Cisco Firepower equipment:Ssd:isUpgradeRequired
        managed object property"
    ::= { cfprEquipmentSsdEntry 8 }

cfprEquipmentSsdModel OBJECT-TYPE
    SYNTAX       SnmpAdminString
    MAX-ACCESS   read-only
    STATUS       current
    DESCRIPTION
        "Cisco Firepower equipment:Ssd:model managed object property"
    ::= { cfprEquipmentSsdEntry 9 }

cfprEquipmentSsdRevision OBJECT-TYPE
    SYNTAX       SnmpAdminString
    MAX-ACCESS   read-only
    STATUS       current
    DESCRIPTION
        "Cisco Firepower equipment:Ssd:revision managed object property"
    ::= { cfprEquipmentSsdEntry 10 }

cfprEquipmentSsdSerial OBJECT-TYPE
    SYNTAX       SnmpAdminString
    MAX-ACCESS   read-only
    STATUS       current
    DESCRIPTION
        "Cisco Firepower equipment:Ssd:serial managed object property"
    ::= { cfprEquipmentSsdEntry 11 }

cfprEquipmentSsdVendor OBJECT-TYPE
    SYNTAX       SnmpAdminString
    MAX-ACCESS   read-only
    STATUS       current
    DESCRIPTION
        "Cisco Firepower equipment:Ssd:vendor managed object property"
    ::= { cfprEquipmentSsdEntry 12 }

cfprEquipmentSwitchCapTable OBJECT-TYPE
    SYNTAX           SEQUENCE OF CfprEquipmentSwitchCapEntry
    MAX-ACCESS       not-accessible
    STATUS           current
    DESCRIPTION
        "Cisco Firepower equipment:SwitchCap managed object table"
    ::= { cfprEquipmentObjects 131 }

cfprEquipmentSwitchCapEntry OBJECT-TYPE
    SYNTAX           CfprEquipmentSwitchCapEntry
    MAX-ACCESS       not-accessible
    STATUS           current
    DESCRIPTION
        "Entry for the cfprEquipmentSwitchCapTable table."
    INDEX { cfprEquipmentSwitchCapInstanceId }
    ::= { cfprEquipmentSwitchCapTable 1 }

CfprEquipmentSwitchCapEntry ::= SEQUENCE {
    cfprEquipmentSwitchCapInstanceId                                 CfprManagedObjectId,
    cfprEquipmentSwitchCapDn                                         CfprManagedObjectDn,
    cfprEquipmentSwitchCapRn                                         SnmpAdminString,
    cfprEquipmentSwitchCapBreakoutIfSupported                        TruthValue,
    cfprEquipmentSwitchCapDescr                                      SnmpAdminString,
    cfprEquipmentSwitchCapFanModulesSupported                        TruthValue,
    cfprEquipmentSwitchCapIntId                                      SnmpAdminString,
    cfprEquipmentSwitchCapLocatorBeaconSupported                     TruthValue,
    cfprEquipmentSwitchCapMaxActiveSpanSessionCount                  Gauge32,
    cfprEquipmentSwitchCapMaxEth1gPort                               Gauge32,
    cfprEquipmentSwitchCapMaxEth1gSlot                               Gauge32,
    cfprEquipmentSwitchCapMaxEthPcMembers                            Gauge32,
    cfprEquipmentSwitchCapMaxEthPcs                                  Gauge32,
    cfprEquipmentSwitchCapMaxFcoePcMembers                           Gauge32,
    cfprEquipmentSwitchCapMaxUplinkPorts                             Gauge32,
    cfprEquipmentSwitchCapMgmtDaughterCardSlotId                     Gauge32,
    cfprEquipmentSwitchCapName                                       SnmpAdminString,
    cfprEquipmentSwitchCapPolicyLevel                                Gauge32,
    cfprEquipmentSwitchCapPolicyOwner                                CfprPolicyPolicyOwner,
    cfprEquipmentSwitchCapSerenoNetflowSupported                     TruthValue
}

cfprEquipmentSwitchCapInstanceId OBJECT-TYPE
    SYNTAX       CfprManagedObjectId
    MAX-ACCESS   not-accessible
    STATUS       current
    DESCRIPTION
        "Instance identifier of the managed object."
    ::= { cfprEquipmentSwitchCapEntry 1 }

cfprEquipmentSwitchCapDn OBJECT-TYPE
    SYNTAX       CfprManagedObjectDn
    MAX-ACCESS   read-only
    STATUS       current
    DESCRIPTION
        "Cisco Firepower equipment:SwitchCap:dn managed object property"
    ::= { cfprEquipmentSwitchCapEntry 2 }

cfprEquipmentSwitchCapRn OBJECT-TYPE
    SYNTAX       SnmpAdminString
    MAX-ACCESS   read-only
    STATUS       current
    DESCRIPTION
        "Cisco Firepower equipment:SwitchCap:rn managed object property"
    ::= { cfprEquipmentSwitchCapEntry 3 }

cfprEquipmentSwitchCapBreakoutIfSupported OBJECT-TYPE
    SYNTAX       TruthValue
    MAX-ACCESS   read-only
    STATUS       current
    DESCRIPTION
        "Cisco Firepower equipment:SwitchCap:breakoutIfSupported
        managed object property"
    ::= { cfprEquipmentSwitchCapEntry 4 }

cfprEquipmentSwitchCapDescr OBJECT-TYPE
    SYNTAX       SnmpAdminString
    MAX-ACCESS   read-only
    STATUS       current
    DESCRIPTION
        "Cisco Firepower equipment:SwitchCap:descr managed
        object property"
    ::= { cfprEquipmentSwitchCapEntry 5 }

cfprEquipmentSwitchCapFanModulesSupported OBJECT-TYPE
    SYNTAX       TruthValue
    MAX-ACCESS   read-only
    STATUS       current
    DESCRIPTION
        "Cisco Firepower equipment:SwitchCap:fanModulesSupported
        managed object property"
    ::= { cfprEquipmentSwitchCapEntry 6 }

cfprEquipmentSwitchCapIntId OBJECT-TYPE
    SYNTAX       SnmpAdminString
    MAX-ACCESS   read-only
    STATUS       current
    DESCRIPTION
        "Cisco Firepower equipment:SwitchCap:intId managed
        object property"
    ::= { cfprEquipmentSwitchCapEntry 7 }

cfprEquipmentSwitchCapLocatorBeaconSupported OBJECT-TYPE
    SYNTAX       TruthValue
    MAX-ACCESS   read-only
    STATUS       current
    DESCRIPTION
        "Cisco Firepower equipment:SwitchCap:locatorBeaconSupported
        managed object property"
    ::= { cfprEquipmentSwitchCapEntry 8 }

cfprEquipmentSwitchCapMaxActiveSpanSessionCount OBJECT-TYPE
    SYNTAX       Gauge32
    MAX-ACCESS   read-only
    STATUS       current
    DESCRIPTION
        "Cisco Firepower equipment:SwitchCap:maxActiveSpanSessionCount
        managed object property"
    ::= { cfprEquipmentSwitchCapEntry 9 }

cfprEquipmentSwitchCapMaxEth1gPort OBJECT-TYPE
    SYNTAX       Gauge32
    MAX-ACCESS   read-only
    STATUS       current
    DESCRIPTION
        "Cisco Firepower equipment:SwitchCap:maxEth1gPort
        managed object property"
    ::= { cfprEquipmentSwitchCapEntry 10 }

cfprEquipmentSwitchCapMaxEth1gSlot OBJECT-TYPE
    SYNTAX       Gauge32
    MAX-ACCESS   read-only
    STATUS       current
    DESCRIPTION
        "Cisco Firepower equipment:SwitchCap:maxEth1gSlot
        managed object property"
    ::= { cfprEquipmentSwitchCapEntry 11 }

cfprEquipmentSwitchCapMaxEthPcMembers OBJECT-TYPE
    SYNTAX       Gauge32
    MAX-ACCESS   read-only
    STATUS       current
    DESCRIPTION
        "Cisco Firepower equipment:SwitchCap:maxEthPcMembers
        managed object property"
    ::= { cfprEquipmentSwitchCapEntry 12 }

cfprEquipmentSwitchCapMaxEthPcs OBJECT-TYPE
    SYNTAX       Gauge32
    MAX-ACCESS   read-only
    STATUS       current
    DESCRIPTION
        "Cisco Firepower equipment:SwitchCap:maxEthPcs
        managed object property"
    ::= { cfprEquipmentSwitchCapEntry 13 }

cfprEquipmentSwitchCapMaxFcoePcMembers OBJECT-TYPE
    SYNTAX       Gauge32
    MAX-ACCESS   read-only
    STATUS       current
    DESCRIPTION
        "Cisco Firepower equipment:SwitchCap:maxFcoePcMembers
        managed object property"
    ::= { cfprEquipmentSwitchCapEntry 14 }

cfprEquipmentSwitchCapMaxUplinkPorts OBJECT-TYPE
    SYNTAX       Gauge32
    MAX-ACCESS   read-only
    STATUS       current
    DESCRIPTION
        "Cisco Firepower equipment:SwitchCap:maxUplinkPorts
        managed object property"
    ::= { cfprEquipmentSwitchCapEntry 15 }

cfprEquipmentSwitchCapMgmtDaughterCardSlotId OBJECT-TYPE
    SYNTAX       Gauge32
    MAX-ACCESS   read-only
    STATUS       current
    DESCRIPTION
        "Cisco Firepower equipment:SwitchCap:mgmtDaughterCardSlotId
        managed object property"
    ::= { cfprEquipmentSwitchCapEntry 16 }

cfprEquipmentSwitchCapName OBJECT-TYPE
    SYNTAX       SnmpAdminString
    MAX-ACCESS   read-only
    STATUS       current
    DESCRIPTION
        "Cisco Firepower equipment:SwitchCap:name managed object property"
    ::= { cfprEquipmentSwitchCapEntry 17 }

cfprEquipmentSwitchCapPolicyLevel OBJECT-TYPE
    SYNTAX       Gauge32
    MAX-ACCESS   read-only
    STATUS       current
    DESCRIPTION
        "Cisco Firepower equipment:SwitchCap:policyLevel
        managed object property"
    ::= { cfprEquipmentSwitchCapEntry 18 }

cfprEquipmentSwitchCapPolicyOwner OBJECT-TYPE
    SYNTAX       CfprPolicyPolicyOwner
    MAX-ACCESS   read-only
    STATUS       current
    DESCRIPTION
        "Cisco Firepower equipment:SwitchCap:policyOwner
        managed object property"
    ::= { cfprEquipmentSwitchCapEntry 19 }

cfprEquipmentSwitchCapSerenoNetflowSupported OBJECT-TYPE
    SYNTAX       TruthValue
    MAX-ACCESS   read-only
    STATUS       current
    DESCRIPTION
        "Cisco Firepower equipment:SwitchCap:serenoNetflowSupported
        managed object property"
    ::= { cfprEquipmentSwitchCapEntry 20 }

cfprEquipmentSwitchCapProviderTable OBJECT-TYPE
    SYNTAX           SEQUENCE OF CfprEquipmentSwitchCapProviderEntry
    MAX-ACCESS       not-accessible
    STATUS           current
    DESCRIPTION
        "Cisco Firepower equipment:SwitchCapProvider managed object table"
    ::= { cfprEquipmentObjects 132 }

cfprEquipmentSwitchCapProviderEntry OBJECT-TYPE
    SYNTAX           CfprEquipmentSwitchCapProviderEntry
    MAX-ACCESS       not-accessible
    STATUS           current
    DESCRIPTION
        "Entry for the cfprEquipmentSwitchCapProviderTable table."
    INDEX { cfprEquipmentSwitchCapProviderInstanceId }
    ::= { cfprEquipmentSwitchCapProviderTable 1 }

CfprEquipmentSwitchCapProviderEntry ::= SEQUENCE {
    cfprEquipmentSwitchCapProviderInstanceId                         CfprManagedObjectId,
    cfprEquipmentSwitchCapProviderDn                                 CfprManagedObjectDn,
    cfprEquipmentSwitchCapProviderRn                                 SnmpAdminString,
    cfprEquipmentSwitchCapProviderDeleted                            TruthValue,
    cfprEquipmentSwitchCapProviderDeprecated                         TruthValue,
    cfprEquipmentSwitchCapProviderElementLoadFailures                Gauge32,
    cfprEquipmentSwitchCapProviderElementsLoaded                     Gauge32,
    cfprEquipmentSwitchCapProviderExpectedMemory                     Gauge32,
    cfprEquipmentSwitchCapProviderGencount                           Gauge32,
    cfprEquipmentSwitchCapProviderLoadErrors                         Gauge32,
    cfprEquipmentSwitchCapProviderLoadWarnings                       Gauge32,
    cfprEquipmentSwitchCapProviderMgmtPlaneVer                       SnmpAdminString,
    cfprEquipmentSwitchCapProviderModel                              SnmpAdminString,
    cfprEquipmentSwitchCapProviderPromCardType                       Gauge32,
    cfprEquipmentSwitchCapProviderRevision                           SnmpAdminString,
    cfprEquipmentSwitchCapProviderVendor                             SnmpAdminString
}

cfprEquipmentSwitchCapProviderInstanceId OBJECT-TYPE
    SYNTAX       CfprManagedObjectId
    MAX-ACCESS   not-accessible
    STATUS       current
    DESCRIPTION
        "Instance identifier of the managed object."
    ::= { cfprEquipmentSwitchCapProviderEntry 1 }

cfprEquipmentSwitchCapProviderDn OBJECT-TYPE
    SYNTAX       CfprManagedObjectDn
    MAX-ACCESS   read-only
    STATUS       current
    DESCRIPTION
        "Cisco Firepower equipment:SwitchCapProvider:dn
        managed object property"
    ::= { cfprEquipmentSwitchCapProviderEntry 2 }

cfprEquipmentSwitchCapProviderRn OBJECT-TYPE
    SYNTAX       SnmpAdminString
    MAX-ACCESS   read-only
    STATUS       current
    DESCRIPTION
        "Cisco Firepower equipment:SwitchCapProvider:rn
        managed object property"
    ::= { cfprEquipmentSwitchCapProviderEntry 3 }

cfprEquipmentSwitchCapProviderDeleted OBJECT-TYPE
    SYNTAX       TruthValue
    MAX-ACCESS   read-only
    STATUS       current
    DESCRIPTION
        "Cisco Firepower equipment:SwitchCapProvider:deleted
        managed object property"
    ::= { cfprEquipmentSwitchCapProviderEntry 4 }

cfprEquipmentSwitchCapProviderDeprecated OBJECT-TYPE
    SYNTAX       TruthValue
    MAX-ACCESS   read-only
    STATUS       current
    DESCRIPTION
        "Cisco Firepower equipment:SwitchCapProvider:deprecated
        managed object property"
    ::= { cfprEquipmentSwitchCapProviderEntry 5 }

cfprEquipmentSwitchCapProviderElementLoadFailures OBJECT-TYPE
    SYNTAX       Gauge32
    MAX-ACCESS   read-only
    STATUS       current
    DESCRIPTION
        "Cisco Firepower equipment:SwitchCapProvider:elementLoadFailures
        managed object property"
    ::= { cfprEquipmentSwitchCapProviderEntry 6 }

cfprEquipmentSwitchCapProviderElementsLoaded OBJECT-TYPE
    SYNTAX       Gauge32
    MAX-ACCESS   read-only
    STATUS       current
    DESCRIPTION
        "Cisco Firepower equipment:SwitchCapProvider:elementsLoaded
        managed object property"
    ::= { cfprEquipmentSwitchCapProviderEntry 7 }

cfprEquipmentSwitchCapProviderExpectedMemory OBJECT-TYPE
    SYNTAX       Gauge32
    MAX-ACCESS   read-only
    STATUS       current
    DESCRIPTION
        "Cisco Firepower equipment:SwitchCapProvider:expectedMemory
        managed object property"
    ::= { cfprEquipmentSwitchCapProviderEntry 8 }

cfprEquipmentSwitchCapProviderGencount OBJECT-TYPE
    SYNTAX       Gauge32
    MAX-ACCESS   read-only
    STATUS       current
    DESCRIPTION
        "Cisco Firepower equipment:SwitchCapProvider:gencount
        managed object property"
    ::= { cfprEquipmentSwitchCapProviderEntry 9 }

cfprEquipmentSwitchCapProviderLoadErrors OBJECT-TYPE
    SYNTAX       Gauge32
    MAX-ACCESS   read-only
    STATUS       current
    DESCRIPTION
        "Cisco Firepower equipment:SwitchCapProvider:loadErrors
        managed object property"
    ::= { cfprEquipmentSwitchCapProviderEntry 10 }

cfprEquipmentSwitchCapProviderLoadWarnings OBJECT-TYPE
    SYNTAX       Gauge32
    MAX-ACCESS   read-only
    STATUS       current
    DESCRIPTION
        "Cisco Firepower equipment:SwitchCapProvider:loadWarnings
        managed object property"
    ::= { cfprEquipmentSwitchCapProviderEntry 11 }

cfprEquipmentSwitchCapProviderMgmtPlaneVer OBJECT-TYPE
    SYNTAX       SnmpAdminString
    MAX-ACCESS   read-only
    STATUS       current
    DESCRIPTION
        "Cisco Firepower equipment:SwitchCapProvider:mgmtPlaneVer
        managed object property"
    ::= { cfprEquipmentSwitchCapProviderEntry 12 }

cfprEquipmentSwitchCapProviderModel OBJECT-TYPE
    SYNTAX       SnmpAdminString
    MAX-ACCESS   read-only
    STATUS       current
    DESCRIPTION
        "Cisco Firepower equipment:SwitchCapProvider:model
        managed object property"
    ::= { cfprEquipmentSwitchCapProviderEntry 13 }

cfprEquipmentSwitchCapProviderPromCardType OBJECT-TYPE
    SYNTAX       Gauge32
    MAX-ACCESS   read-only
    STATUS       current
    DESCRIPTION
        "Cisco Firepower equipment:SwitchCapProvider:promCardType
        managed object property"
    ::= { cfprEquipmentSwitchCapProviderEntry 14 }

cfprEquipmentSwitchCapProviderRevision OBJECT-TYPE
    SYNTAX       SnmpAdminString
    MAX-ACCESS   read-only
    STATUS       current
    DESCRIPTION
        "Cisco Firepower equipment:SwitchCapProvider:revision
        managed object property"
    ::= { cfprEquipmentSwitchCapProviderEntry 15 }

cfprEquipmentSwitchCapProviderVendor OBJECT-TYPE
    SYNTAX       SnmpAdminString
    MAX-ACCESS   read-only
    STATUS       current
    DESCRIPTION
        "Cisco Firepower equipment:SwitchCapProvider:vendor
        managed object property"
    ::= { cfprEquipmentSwitchCapProviderEntry 16 }

cfprEquipmentSwitchCardTable OBJECT-TYPE
    SYNTAX           SEQUENCE OF CfprEquipmentSwitchCardEntry
    MAX-ACCESS       not-accessible
    STATUS           current
    DESCRIPTION
        "Cisco Firepower equipment:SwitchCard managed object table"
    ::= { cfprEquipmentObjects 133 }

cfprEquipmentSwitchCardEntry OBJECT-TYPE
    SYNTAX           CfprEquipmentSwitchCardEntry
    MAX-ACCESS       not-accessible
    STATUS           current
    DESCRIPTION
        "Entry for the cfprEquipmentSwitchCardTable table."
    INDEX { cfprEquipmentSwitchCardInstanceId }
    ::= { cfprEquipmentSwitchCardTable 1 }

CfprEquipmentSwitchCardEntry ::= SEQUENCE {
    cfprEquipmentSwitchCardInstanceId                                CfprManagedObjectId,
    cfprEquipmentSwitchCardDn                                        CfprManagedObjectDn,
    cfprEquipmentSwitchCardRn                                        SnmpAdminString,
    cfprEquipmentSwitchCardAct2FailState                             TruthValue,
    cfprEquipmentSwitchCardDescr                                     SnmpAdminString,
    cfprEquipmentSwitchCardFltAggr                                   Unsigned64,
    cfprEquipmentSwitchCardId                                        Gauge32,
    cfprEquipmentSwitchCardModel                                     SnmpAdminString,
    cfprEquipmentSwitchCardNumPorts                                  Gauge32,
    cfprEquipmentSwitchCardOperQualifierReason                       SnmpAdminString,
    cfprEquipmentSwitchCardOperState                                 CfprEquipmentOperability,
    cfprEquipmentSwitchCardOperability                               CfprEquipmentOperability,
    cfprEquipmentSwitchCardPerf                                      CfprEquipmentSensorThresholdStatus,
    cfprEquipmentSwitchCardPower                                     CfprEquipmentPowerState,
    cfprEquipmentSwitchCardPresence                                  CfprEquipmentPresence,
    cfprEquipmentSwitchCardRevision                                  SnmpAdminString,
    cfprEquipmentSwitchCardSerial                                    SnmpAdminString,
    cfprEquipmentSwitchCardState                                     CfprEquipmentPowerState,
    cfprEquipmentSwitchCardThermal                                   CfprEquipmentSensorThresholdStatus,
    cfprEquipmentSwitchCardTs                                        DateAndTime,
    cfprEquipmentSwitchCardVendor                                    SnmpAdminString,
    cfprEquipmentSwitchCardVoltage                                   CfprEquipmentSensorThresholdStatus,
    cfprEquipmentSwitchCardAdminState                                CfprEquipmentCardAdminState,
    cfprEquipmentSwitchCardMaxUserPort                               Gauge32,
    cfprEquipmentSwitchCardVid                                       SnmpAdminString
}

cfprEquipmentSwitchCardInstanceId OBJECT-TYPE
    SYNTAX       CfprManagedObjectId
    MAX-ACCESS   not-accessible
    STATUS       current
    DESCRIPTION
        "Instance identifier of the managed object."
    ::= { cfprEquipmentSwitchCardEntry 1 }

cfprEquipmentSwitchCardDn OBJECT-TYPE
    SYNTAX       CfprManagedObjectDn
    MAX-ACCESS   read-only
    STATUS       current
    DESCRIPTION
        "Cisco Firepower equipment:SwitchCard:dn managed object property"
    ::= { cfprEquipmentSwitchCardEntry 2 }

cfprEquipmentSwitchCardRn OBJECT-TYPE
    SYNTAX       SnmpAdminString
    MAX-ACCESS   read-only
    STATUS       current
    DESCRIPTION
        "Cisco Firepower equipment:SwitchCard:rn managed object property"
    ::= { cfprEquipmentSwitchCardEntry 3 }

cfprEquipmentSwitchCardAct2FailState OBJECT-TYPE
    SYNTAX       TruthValue
    MAX-ACCESS   read-only
    STATUS       current
    DESCRIPTION
        "Cisco Firepower equipment:SwitchCard:act2FailState
        managed object property"
    ::= { cfprEquipmentSwitchCardEntry 4 }

cfprEquipmentSwitchCardDescr OBJECT-TYPE
    SYNTAX       SnmpAdminString
    MAX-ACCESS   read-only
    STATUS       current
    DESCRIPTION
        "Cisco Firepower equipment:SwitchCard:descr managed
        object property"
    ::= { cfprEquipmentSwitchCardEntry 5 }

cfprEquipmentSwitchCardFltAggr OBJECT-TYPE
    SYNTAX       Unsigned64
    MAX-ACCESS   read-only
    STATUS       current
    DESCRIPTION
        "Cisco Firepower equipment:SwitchCard:fltAggr managed
        object property"
    ::= { cfprEquipmentSwitchCardEntry 6 }

cfprEquipmentSwitchCardId OBJECT-TYPE
    SYNTAX       Gauge32
    MAX-ACCESS   read-only
    STATUS       current
    DESCRIPTION
        "Cisco Firepower equipment:SwitchCard:id managed object property"
    ::= { cfprEquipmentSwitchCardEntry 7 }

cfprEquipmentSwitchCardModel OBJECT-TYPE
    SYNTAX       SnmpAdminString
    MAX-ACCESS   read-only
    STATUS       current
    DESCRIPTION
        "Cisco Firepower equipment:SwitchCard:model managed
        object property"
    ::= { cfprEquipmentSwitchCardEntry 8 }

cfprEquipmentSwitchCardNumPorts OBJECT-TYPE
    SYNTAX       Gauge32
    MAX-ACCESS   read-only
    STATUS       current
    DESCRIPTION
        "Cisco Firepower equipment:SwitchCard:numPorts
        managed object property"
    ::= { cfprEquipmentSwitchCardEntry 9 }

cfprEquipmentSwitchCardOperQualifierReason OBJECT-TYPE
    SYNTAX       SnmpAdminString
    MAX-ACCESS   read-only
    STATUS       current
    DESCRIPTION
        "Cisco Firepower equipment:SwitchCard:operQualifierReason
        managed object property"
    ::= { cfprEquipmentSwitchCardEntry 10 }

cfprEquipmentSwitchCardOperState OBJECT-TYPE
    SYNTAX       CfprEquipmentOperability
    MAX-ACCESS   read-only
    STATUS       current
    DESCRIPTION
        "Cisco Firepower equipment:SwitchCard:operState
        managed object property"
    ::= { cfprEquipmentSwitchCardEntry 11 }

cfprEquipmentSwitchCardOperability OBJECT-TYPE
    SYNTAX       CfprEquipmentOperability
    MAX-ACCESS   read-only
    STATUS       current
    DESCRIPTION
        "Cisco Firepower equipment:SwitchCard:operability
        managed object property"
    ::= { cfprEquipmentSwitchCardEntry 12 }

cfprEquipmentSwitchCardPerf OBJECT-TYPE
    SYNTAX       CfprEquipmentSensorThresholdStatus
    MAX-ACCESS   read-only
    STATUS       current
    DESCRIPTION
        "Cisco Firepower equipment:SwitchCard:perf managed
        object property"
    ::= { cfprEquipmentSwitchCardEntry 13 }

cfprEquipmentSwitchCardPower OBJECT-TYPE
    SYNTAX       CfprEquipmentPowerState
    MAX-ACCESS   read-only
    STATUS       current
    DESCRIPTION
        "Cisco Firepower equipment:SwitchCard:power managed
        object property"
    ::= { cfprEquipmentSwitchCardEntry 14 }

cfprEquipmentSwitchCardPresence OBJECT-TYPE
    SYNTAX       CfprEquipmentPresence
    MAX-ACCESS   read-only
    STATUS       current
    DESCRIPTION
        "Cisco Firepower equipment:SwitchCard:presence
        managed object property"
    ::= { cfprEquipmentSwitchCardEntry 15 }

cfprEquipmentSwitchCardRevision OBJECT-TYPE
    SYNTAX       SnmpAdminString
    MAX-ACCESS   read-only
    STATUS       current
    DESCRIPTION
        "Cisco Firepower equipment:SwitchCard:revision
        managed object property"
    ::= { cfprEquipmentSwitchCardEntry 16 }

cfprEquipmentSwitchCardSerial OBJECT-TYPE
    SYNTAX       SnmpAdminString
    MAX-ACCESS   read-only
    STATUS       current
    DESCRIPTION
        "Cisco Firepower equipment:SwitchCard:serial managed
        object property"
    ::= { cfprEquipmentSwitchCardEntry 17 }

cfprEquipmentSwitchCardState OBJECT-TYPE
    SYNTAX       CfprEquipmentPowerState
    MAX-ACCESS   read-only
    STATUS       current
    DESCRIPTION
        "Cisco Firepower equipment:SwitchCard:state managed
        object property"
    ::= { cfprEquipmentSwitchCardEntry 18 }

cfprEquipmentSwitchCardThermal OBJECT-TYPE
    SYNTAX       CfprEquipmentSensorThresholdStatus
    MAX-ACCESS   read-only
    STATUS       current
    DESCRIPTION
        "Cisco Firepower equipment:SwitchCard:thermal managed
        object property"
    ::= { cfprEquipmentSwitchCardEntry 19 }

cfprEquipmentSwitchCardTs OBJECT-TYPE
    SYNTAX       DateAndTime
    MAX-ACCESS   read-only
    STATUS       current
    DESCRIPTION
        "Cisco Firepower equipment:SwitchCard:ts managed object property"
    ::= { cfprEquipmentSwitchCardEntry 20 }

cfprEquipmentSwitchCardVendor OBJECT-TYPE
    SYNTAX       SnmpAdminString
    MAX-ACCESS   read-only
    STATUS       current
    DESCRIPTION
        "Cisco Firepower equipment:SwitchCard:vendor managed
        object property"
    ::= { cfprEquipmentSwitchCardEntry 21 }

cfprEquipmentSwitchCardVoltage OBJECT-TYPE
    SYNTAX       CfprEquipmentSensorThresholdStatus
    MAX-ACCESS   read-only
    STATUS       current
    DESCRIPTION
        "Cisco Firepower equipment:SwitchCard:voltage managed
        object property"
    ::= { cfprEquipmentSwitchCardEntry 22 }

cfprEquipmentSwitchCardAdminState OBJECT-TYPE
    SYNTAX       CfprEquipmentCardAdminState
    MAX-ACCESS   read-only
    STATUS       current
    DESCRIPTION
        "Cisco Firepower equipment:SwitchCard:adminState
        managed object property"
    ::= { cfprEquipmentSwitchCardEntry 23 }

cfprEquipmentSwitchCardMaxUserPort OBJECT-TYPE
    SYNTAX       Gauge32
    MAX-ACCESS   read-only
    STATUS       current
    DESCRIPTION
        "Cisco Firepower equipment:SwitchCard:maxUserPort
        managed object property"
    ::= { cfprEquipmentSwitchCardEntry 24 }

cfprEquipmentSwitchCardVid OBJECT-TYPE
    SYNTAX       SnmpAdminString
    MAX-ACCESS   read-only
    STATUS       current
    DESCRIPTION
        "Cisco Firepower equipment:SwitchCard:vid managed object property"
    ::= { cfprEquipmentSwitchCardEntry 25 }

cfprEquipmentSwitchIOCardTable OBJECT-TYPE
    SYNTAX           SEQUENCE OF CfprEquipmentSwitchIOCardEntry
    MAX-ACCESS       not-accessible
    STATUS           current
    DESCRIPTION
        "Cisco Firepower equipment:SwitchIOCard managed object table"
    ::= { cfprEquipmentObjects 134 }

cfprEquipmentSwitchIOCardEntry OBJECT-TYPE
    SYNTAX           CfprEquipmentSwitchIOCardEntry
    MAX-ACCESS       not-accessible
    STATUS           current
    DESCRIPTION
        "Entry for the cfprEquipmentSwitchIOCardTable table."
    INDEX { cfprEquipmentSwitchIOCardInstanceId }
    ::= { cfprEquipmentSwitchIOCardTable 1 }

CfprEquipmentSwitchIOCardEntry ::= SEQUENCE {
    cfprEquipmentSwitchIOCardInstanceId                              CfprManagedObjectId,
    cfprEquipmentSwitchIOCardDn                                      CfprManagedObjectDn,
    cfprEquipmentSwitchIOCardRn                                      SnmpAdminString,
    cfprEquipmentSwitchIOCardAdminPowerState                         CfprEquipmentAdminPowerState,
    cfprEquipmentSwitchIOCardBaseAddr                                InetAddressIPv4,
    cfprEquipmentSwitchIOCardChassisId                               Gauge32,
    cfprEquipmentSwitchIOCardConfigState                             CfprEquipmentChassisConfigState,
    cfprEquipmentSwitchIOCardDiscovery                               CfprEquipmentDiscoveryState,
    cfprEquipmentSwitchIOCardFeOfflineTs                             Unsigned64,
    cfprEquipmentSwitchIOCardFeReadyTs                               Unsigned64,
    cfprEquipmentSwitchIOCardFltAggr                                 Unsigned64,
    cfprEquipmentSwitchIOCardFsmDescr                                SnmpAdminString,
    cfprEquipmentSwitchIOCardFsmFlags                                SnmpAdminString,
    cfprEquipmentSwitchIOCardFsmPrev                                 SnmpAdminString,
    cfprEquipmentSwitchIOCardFsmProgr                                Gauge32,
    cfprEquipmentSwitchIOCardFsmRmtInvErrCode                        Gauge32,
    cfprEquipmentSwitchIOCardFsmRmtInvErrDescr                       SnmpAdminString,
    cfprEquipmentSwitchIOCardFsmRmtInvRslt                           CfprConditionRemoteInvRslt,
    cfprEquipmentSwitchIOCardFsmStageDescr                           SnmpAdminString,
    cfprEquipmentSwitchIOCardFsmStamp                                DateAndTime,
    cfprEquipmentSwitchIOCardFsmStatus                               SnmpAdminString,
    cfprEquipmentSwitchIOCardFsmTry                                  Gauge32,
    cfprEquipmentSwitchIOCardId                                      CfprEquipmentSwitchIOCardId,
    cfprEquipmentSwitchIOCardLcName                                  SnmpAdminString,
    cfprEquipmentSwitchIOCardLcTs                                    DateAndTime,
    cfprEquipmentSwitchIOCardMfgTime                                 DateAndTime,
    cfprEquipmentSwitchIOCardModel                                   SnmpAdminString,
    cfprEquipmentSwitchIOCardOperQualifier                           CfprEquipmentIOCardIssues,
    cfprEquipmentSwitchIOCardOperQualifierReason                     SnmpAdminString,
    cfprEquipmentSwitchIOCardOperState                               CfprEquipmentOperability,
    cfprEquipmentSwitchIOCardOperability                             CfprEquipmentOperability,
    cfprEquipmentSwitchIOCardPeerCommStatus                          CfprEquipmentCommStatus,
    cfprEquipmentSwitchIOCardPeerDn                                  SnmpAdminString,
    cfprEquipmentSwitchIOCardPerf                                    CfprEquipmentSensorThresholdStatus,
    cfprEquipmentSwitchIOCardPower                                   CfprEquipmentPowerState,
    cfprEquipmentSwitchIOCardPresence                                CfprEquipmentPresence,
    cfprEquipmentSwitchIOCardProcessorThermalState                   CfprEquipmentSensorThresholdStatus,
    cfprEquipmentSwitchIOCardRevision                                SnmpAdminString,
    cfprEquipmentSwitchIOCardSerial                                  SnmpAdminString,
    cfprEquipmentSwitchIOCardSide                                    CfprNetworkSide,
    cfprEquipmentSwitchIOCardSwitchId                                CfprNetworkSwitchId,
    cfprEquipmentSwitchIOCardThermal                                 CfprEquipmentSensorThresholdStatus,
    cfprEquipmentSwitchIOCardUpgradeStatus                           CfprMgmtUpgradeStatus,
    cfprEquipmentSwitchIOCardUsrLbl                                  SnmpAdminString,
    cfprEquipmentSwitchIOCardVendor                                  SnmpAdminString,
    cfprEquipmentSwitchIOCardVoltage                                 CfprEquipmentSensorThresholdStatus
}

cfprEquipmentSwitchIOCardInstanceId OBJECT-TYPE
    SYNTAX       CfprManagedObjectId
    MAX-ACCESS   not-accessible
    STATUS       current
    DESCRIPTION
        "Instance identifier of the managed object."
    ::= { cfprEquipmentSwitchIOCardEntry 1 }

cfprEquipmentSwitchIOCardDn OBJECT-TYPE
    SYNTAX       CfprManagedObjectDn
    MAX-ACCESS   read-only
    STATUS       current
    DESCRIPTION
        "Cisco Firepower equipment:SwitchIOCard:dn managed
        object property"
    ::= { cfprEquipmentSwitchIOCardEntry 2 }

cfprEquipmentSwitchIOCardRn OBJECT-TYPE
    SYNTAX       SnmpAdminString
    MAX-ACCESS   read-only
    STATUS       current
    DESCRIPTION
        "Cisco Firepower equipment:SwitchIOCard:rn managed
        object property"
    ::= { cfprEquipmentSwitchIOCardEntry 3 }

cfprEquipmentSwitchIOCardAdminPowerState OBJECT-TYPE
    SYNTAX       CfprEquipmentAdminPowerState
    MAX-ACCESS   read-only
    STATUS       current
    DESCRIPTION
        "Cisco Firepower equipment:SwitchIOCard:adminPowerState
        managed object property"
    ::= { cfprEquipmentSwitchIOCardEntry 4 }

cfprEquipmentSwitchIOCardBaseAddr OBJECT-TYPE
    SYNTAX       InetAddressIPv4
    MAX-ACCESS   read-only
    STATUS       current
    DESCRIPTION
        "Cisco Firepower equipment:SwitchIOCard:baseAddr
        managed object property"
    ::= { cfprEquipmentSwitchIOCardEntry 5 }

cfprEquipmentSwitchIOCardChassisId OBJECT-TYPE
    SYNTAX       Gauge32
    MAX-ACCESS   read-only
    STATUS       current
    DESCRIPTION
        "Cisco Firepower equipment:SwitchIOCard:chassisId
        managed object property"
    ::= { cfprEquipmentSwitchIOCardEntry 6 }

cfprEquipmentSwitchIOCardConfigState OBJECT-TYPE
    SYNTAX       CfprEquipmentChassisConfigState
    MAX-ACCESS   read-only
    STATUS       current
    DESCRIPTION
        "Cisco Firepower equipment:SwitchIOCard:configState
        managed object property"
    ::= { cfprEquipmentSwitchIOCardEntry 7 }

cfprEquipmentSwitchIOCardDiscovery OBJECT-TYPE
    SYNTAX       CfprEquipmentDiscoveryState
    MAX-ACCESS   read-only
    STATUS       current
    DESCRIPTION
        "Cisco Firepower equipment:SwitchIOCard:discovery
        managed object property"
    ::= { cfprEquipmentSwitchIOCardEntry 8 }

cfprEquipmentSwitchIOCardFeOfflineTs OBJECT-TYPE
    SYNTAX       Unsigned64
    MAX-ACCESS   read-only
    STATUS       current
    DESCRIPTION
        "Cisco Firepower equipment:SwitchIOCard:feOfflineTs
        managed object property"
    ::= { cfprEquipmentSwitchIOCardEntry 9 }

cfprEquipmentSwitchIOCardFeReadyTs OBJECT-TYPE
    SYNTAX       Unsigned64
    MAX-ACCESS   read-only
    STATUS       current
    DESCRIPTION
        "Cisco Firepower equipment:SwitchIOCard:feReadyTs
        managed object property"
    ::= { cfprEquipmentSwitchIOCardEntry 10 }

cfprEquipmentSwitchIOCardFltAggr OBJECT-TYPE
    SYNTAX       Unsigned64
    MAX-ACCESS   read-only
    STATUS       current
    DESCRIPTION
        "Cisco Firepower equipment:SwitchIOCard:fltAggr
        managed object property"
    ::= { cfprEquipmentSwitchIOCardEntry 11 }

cfprEquipmentSwitchIOCardFsmDescr OBJECT-TYPE
    SYNTAX       SnmpAdminString
    MAX-ACCESS   read-only
    STATUS       current
    DESCRIPTION
        "Cisco Firepower equipment:SwitchIOCard:fsmDescr
        managed object property"
    ::= { cfprEquipmentSwitchIOCardEntry 12 }

cfprEquipmentSwitchIOCardFsmFlags OBJECT-TYPE
    SYNTAX       SnmpAdminString
    MAX-ACCESS   read-only
    STATUS       current
    DESCRIPTION
        "Cisco Firepower equipment:SwitchIOCard:fsmFlags
        managed object property"
    ::= { cfprEquipmentSwitchIOCardEntry 13 }

cfprEquipmentSwitchIOCardFsmPrev OBJECT-TYPE
    SYNTAX       SnmpAdminString
    MAX-ACCESS   read-only
    STATUS       current
    DESCRIPTION
        "Cisco Firepower equipment:SwitchIOCard:fsmPrev
        managed object property"
    ::= { cfprEquipmentSwitchIOCardEntry 14 }

cfprEquipmentSwitchIOCardFsmProgr OBJECT-TYPE
    SYNTAX       Gauge32
    MAX-ACCESS   read-only
    STATUS       current
    DESCRIPTION
        "Cisco Firepower equipment:SwitchIOCard:fsmProgr
        managed object property"
    ::= { cfprEquipmentSwitchIOCardEntry 15 }

cfprEquipmentSwitchIOCardFsmRmtInvErrCode OBJECT-TYPE
    SYNTAX       Gauge32
    MAX-ACCESS   read-only
    STATUS       current
    DESCRIPTION
        "Cisco Firepower equipment:SwitchIOCard:fsmRmtInvErrCode
        managed object property"
    ::= { cfprEquipmentSwitchIOCardEntry 16 }

cfprEquipmentSwitchIOCardFsmRmtInvErrDescr OBJECT-TYPE
    SYNTAX       SnmpAdminString
    MAX-ACCESS   read-only
    STATUS       current
    DESCRIPTION
        "Cisco Firepower equipment:SwitchIOCard:fsmRmtInvErrDescr
        managed object property"
    ::= { cfprEquipmentSwitchIOCardEntry 17 }

cfprEquipmentSwitchIOCardFsmRmtInvRslt OBJECT-TYPE
    SYNTAX       CfprConditionRemoteInvRslt
    MAX-ACCESS   read-only
    STATUS       current
    DESCRIPTION
        "Cisco Firepower equipment:SwitchIOCard:fsmRmtInvRslt
        managed object property"
    ::= { cfprEquipmentSwitchIOCardEntry 18 }

cfprEquipmentSwitchIOCardFsmStageDescr OBJECT-TYPE
    SYNTAX       SnmpAdminString
    MAX-ACCESS   read-only
    STATUS       current
    DESCRIPTION
        "Cisco Firepower equipment:SwitchIOCard:fsmStageDescr
        managed object property"
    ::= { cfprEquipmentSwitchIOCardEntry 19 }

cfprEquipmentSwitchIOCardFsmStamp OBJECT-TYPE
    SYNTAX       DateAndTime
    MAX-ACCESS   read-only
    STATUS       current
    DESCRIPTION
        "Cisco Firepower equipment:SwitchIOCard:fsmStamp
        managed object property"
    ::= { cfprEquipmentSwitchIOCardEntry 20 }

cfprEquipmentSwitchIOCardFsmStatus OBJECT-TYPE
    SYNTAX       SnmpAdminString
    MAX-ACCESS   read-only
    STATUS       current
    DESCRIPTION
        "Cisco Firepower equipment:SwitchIOCard:fsmStatus
        managed object property"
    ::= { cfprEquipmentSwitchIOCardEntry 21 }

cfprEquipmentSwitchIOCardFsmTry OBJECT-TYPE
    SYNTAX       Gauge32
    MAX-ACCESS   read-only
    STATUS       current
    DESCRIPTION
        "Cisco Firepower equipment:SwitchIOCard:fsmTry
        managed object property"
    ::= { cfprEquipmentSwitchIOCardEntry 22 }

cfprEquipmentSwitchIOCardId OBJECT-TYPE
    SYNTAX       CfprEquipmentSwitchIOCardId
    MAX-ACCESS   read-only
    STATUS       current
    DESCRIPTION
        "Cisco Firepower equipment:SwitchIOCard:id managed
        object property"
    ::= { cfprEquipmentSwitchIOCardEntry 23 }

cfprEquipmentSwitchIOCardLcName OBJECT-TYPE
    SYNTAX       SnmpAdminString
    MAX-ACCESS   read-only
    STATUS       current
    DESCRIPTION
        "Cisco Firepower equipment:SwitchIOCard:lcName
        managed object property"
    ::= { cfprEquipmentSwitchIOCardEntry 24 }

cfprEquipmentSwitchIOCardLcTs OBJECT-TYPE
    SYNTAX       DateAndTime
    MAX-ACCESS   read-only
    STATUS       current
    DESCRIPTION
        "Cisco Firepower equipment:SwitchIOCard:lcTs managed
        object property"
    ::= { cfprEquipmentSwitchIOCardEntry 25 }

cfprEquipmentSwitchIOCardMfgTime OBJECT-TYPE
    SYNTAX       DateAndTime
    MAX-ACCESS   read-only
    STATUS       current
    DESCRIPTION
        "Cisco Firepower equipment:SwitchIOCard:mfgTime
        managed object property"
    ::= { cfprEquipmentSwitchIOCardEntry 26 }

cfprEquipmentSwitchIOCardModel OBJECT-TYPE
    SYNTAX       SnmpAdminString
    MAX-ACCESS   read-only
    STATUS       current
    DESCRIPTION
        "Cisco Firepower equipment:SwitchIOCard:model managed
        object property"
    ::= { cfprEquipmentSwitchIOCardEntry 27 }

cfprEquipmentSwitchIOCardOperQualifier OBJECT-TYPE
    SYNTAX       CfprEquipmentIOCardIssues
    MAX-ACCESS   read-only
    STATUS       current
    DESCRIPTION
        "Cisco Firepower equipment:SwitchIOCard:operQualifier
        managed object property"
    ::= { cfprEquipmentSwitchIOCardEntry 28 }

cfprEquipmentSwitchIOCardOperQualifierReason OBJECT-TYPE
    SYNTAX       SnmpAdminString
    MAX-ACCESS   read-only
    STATUS       current
    DESCRIPTION
        "Cisco Firepower equipment:SwitchIOCard:operQualifierReason
        managed object property"
    ::= { cfprEquipmentSwitchIOCardEntry 29 }

cfprEquipmentSwitchIOCardOperState OBJECT-TYPE
    SYNTAX       CfprEquipmentOperability
    MAX-ACCESS   read-only
    STATUS       current
    DESCRIPTION
        "Cisco Firepower equipment:SwitchIOCard:operState
        managed object property"
    ::= { cfprEquipmentSwitchIOCardEntry 30 }

cfprEquipmentSwitchIOCardOperability OBJECT-TYPE
    SYNTAX       CfprEquipmentOperability
    MAX-ACCESS   read-only
    STATUS       current
    DESCRIPTION
        "Cisco Firepower equipment:SwitchIOCard:operability
        managed object property"
    ::= { cfprEquipmentSwitchIOCardEntry 31 }

cfprEquipmentSwitchIOCardPeerCommStatus OBJECT-TYPE
    SYNTAX       CfprEquipmentCommStatus
    MAX-ACCESS   read-only
    STATUS       current
    DESCRIPTION
        "Cisco Firepower equipment:SwitchIOCard:peerCommStatus
        managed object property"
    ::= { cfprEquipmentSwitchIOCardEntry 32 }

cfprEquipmentSwitchIOCardPeerDn OBJECT-TYPE
    SYNTAX       SnmpAdminString
    MAX-ACCESS   read-only
    STATUS       current
    DESCRIPTION
        "Cisco Firepower equipment:SwitchIOCard:peerDn
        managed object property"
    ::= { cfprEquipmentSwitchIOCardEntry 33 }

cfprEquipmentSwitchIOCardPerf OBJECT-TYPE
    SYNTAX       CfprEquipmentSensorThresholdStatus
    MAX-ACCESS   read-only
    STATUS       current
    DESCRIPTION
        "Cisco Firepower equipment:SwitchIOCard:perf managed
        object property"
    ::= { cfprEquipmentSwitchIOCardEntry 34 }

cfprEquipmentSwitchIOCardPower OBJECT-TYPE
    SYNTAX       CfprEquipmentPowerState
    MAX-ACCESS   read-only
    STATUS       current
    DESCRIPTION
        "Cisco Firepower equipment:SwitchIOCard:power managed
        object property"
    ::= { cfprEquipmentSwitchIOCardEntry 35 }

cfprEquipmentSwitchIOCardPresence OBJECT-TYPE
    SYNTAX       CfprEquipmentPresence
    MAX-ACCESS   read-only
    STATUS       current
    DESCRIPTION
        "Cisco Firepower equipment:SwitchIOCard:presence
        managed object property"
    ::= { cfprEquipmentSwitchIOCardEntry 36 }

cfprEquipmentSwitchIOCardProcessorThermalState OBJECT-TYPE
    SYNTAX       CfprEquipmentSensorThresholdStatus
    MAX-ACCESS   read-only
    STATUS       current
    DESCRIPTION
        "Cisco Firepower equipment:SwitchIOCard:processorThermalState
        managed object property"
    ::= { cfprEquipmentSwitchIOCardEntry 37 }

cfprEquipmentSwitchIOCardRevision OBJECT-TYPE
    SYNTAX       SnmpAdminString
    MAX-ACCESS   read-only
    STATUS       current
    DESCRIPTION
        "Cisco Firepower equipment:SwitchIOCard:revision
        managed object property"
    ::= { cfprEquipmentSwitchIOCardEntry 38 }

cfprEquipmentSwitchIOCardSerial OBJECT-TYPE
    SYNTAX       SnmpAdminString
    MAX-ACCESS   read-only
    STATUS       current
    DESCRIPTION
        "Cisco Firepower equipment:SwitchIOCard:serial
        managed object property"
    ::= { cfprEquipmentSwitchIOCardEntry 39 }

cfprEquipmentSwitchIOCardSide OBJECT-TYPE
    SYNTAX       CfprNetworkSide
    MAX-ACCESS   read-only
    STATUS       current
    DESCRIPTION
        "Cisco Firepower equipment:SwitchIOCard:side managed
        object property"
    ::= { cfprEquipmentSwitchIOCardEntry 40 }

cfprEquipmentSwitchIOCardSwitchId OBJECT-TYPE
    SYNTAX       CfprNetworkSwitchId
    MAX-ACCESS   read-only
    STATUS       current
    DESCRIPTION
        "Cisco Firepower equipment:SwitchIOCard:switchId
        managed object property"
    ::= { cfprEquipmentSwitchIOCardEntry 41 }

cfprEquipmentSwitchIOCardThermal OBJECT-TYPE
    SYNTAX       CfprEquipmentSensorThresholdStatus
    MAX-ACCESS   read-only
    STATUS       current
    DESCRIPTION
        "Cisco Firepower equipment:SwitchIOCard:thermal
        managed object property"
    ::= { cfprEquipmentSwitchIOCardEntry 42 }

cfprEquipmentSwitchIOCardUpgradeStatus OBJECT-TYPE
    SYNTAX       CfprMgmtUpgradeStatus
    MAX-ACCESS   read-only
    STATUS       current
    DESCRIPTION
        "Cisco Firepower equipment:SwitchIOCard:upgradeStatus
        managed object property"
    ::= { cfprEquipmentSwitchIOCardEntry 43 }

cfprEquipmentSwitchIOCardUsrLbl OBJECT-TYPE
    SYNTAX       SnmpAdminString
    MAX-ACCESS   read-only
    STATUS       current
    DESCRIPTION
        "Cisco Firepower equipment:SwitchIOCard:usrLbl
        managed object property"
    ::= { cfprEquipmentSwitchIOCardEntry 44 }

cfprEquipmentSwitchIOCardVendor OBJECT-TYPE
    SYNTAX       SnmpAdminString
    MAX-ACCESS   read-only
    STATUS       current
    DESCRIPTION
        "Cisco Firepower equipment:SwitchIOCard:vendor
        managed object property"
    ::= { cfprEquipmentSwitchIOCardEntry 45 }

cfprEquipmentSwitchIOCardVoltage OBJECT-TYPE
    SYNTAX       CfprEquipmentSensorThresholdStatus
    MAX-ACCESS   read-only
    STATUS       current
    DESCRIPTION
        "Cisco Firepower equipment:SwitchIOCard:voltage
        managed object property"
    ::= { cfprEquipmentSwitchIOCardEntry 46 }

cfprEquipmentSwitchIOCardCapProviderTable OBJECT-TYPE
    SYNTAX           SEQUENCE OF CfprEquipmentSwitchIOCardCapProviderEntry
    MAX-ACCESS       not-accessible
    STATUS           current
    DESCRIPTION
        "Cisco Firepower equipment:SwitchIOCardCapProvider
        managed object table"
    ::= { cfprEquipmentObjects 135 }

cfprEquipmentSwitchIOCardCapProviderEntry OBJECT-TYPE
    SYNTAX           CfprEquipmentSwitchIOCardCapProviderEntry
    MAX-ACCESS       not-accessible
    STATUS           current
    DESCRIPTION
        "Entry for the cfprEquipmentSwitchIOCardCapProviderTable table."
    INDEX { cfprEquipmentSwitchIOCardCapProviderInstanceId }
    ::= { cfprEquipmentSwitchIOCardCapProviderTable 1 }

CfprEquipmentSwitchIOCardCapProviderEntry ::= SEQUENCE {
    cfprEquipmentSwitchIOCardCapProviderInstanceId                   CfprManagedObjectId,
    cfprEquipmentSwitchIOCardCapProviderDn                           CfprManagedObjectDn,
    cfprEquipmentSwitchIOCardCapProviderRn                           SnmpAdminString,
    cfprEquipmentSwitchIOCardCapProviderDeleted                      TruthValue,
    cfprEquipmentSwitchIOCardCapProviderDeprecated                   TruthValue,
    cfprEquipmentSwitchIOCardCapProviderElementLoadFailures          Gauge32,
    cfprEquipmentSwitchIOCardCapProviderElementsLoaded               Gauge32,
    cfprEquipmentSwitchIOCardCapProviderGencount                     Gauge32,
    cfprEquipmentSwitchIOCardCapProviderLoadErrors                   Gauge32,
    cfprEquipmentSwitchIOCardCapProviderLoadWarnings                 Gauge32,
    cfprEquipmentSwitchIOCardCapProviderMgmtPlaneVer                 SnmpAdminString,
    cfprEquipmentSwitchIOCardCapProviderModel                        SnmpAdminString,
    cfprEquipmentSwitchIOCardCapProviderPromCardType                 Gauge32,
    cfprEquipmentSwitchIOCardCapProviderRevision                     SnmpAdminString,
    cfprEquipmentSwitchIOCardCapProviderVendor                       SnmpAdminString
}

cfprEquipmentSwitchIOCardCapProviderInstanceId OBJECT-TYPE
    SYNTAX       CfprManagedObjectId
    MAX-ACCESS   not-accessible
    STATUS       current
    DESCRIPTION
        "Instance identifier of the managed object."
    ::= { cfprEquipmentSwitchIOCardCapProviderEntry 1 }

cfprEquipmentSwitchIOCardCapProviderDn OBJECT-TYPE
    SYNTAX       CfprManagedObjectDn
    MAX-ACCESS   read-only
    STATUS       current
    DESCRIPTION
        "Cisco Firepower equipment:SwitchIOCardCapProvider:dn
        managed object property"
    ::= { cfprEquipmentSwitchIOCardCapProviderEntry 2 }

cfprEquipmentSwitchIOCardCapProviderRn OBJECT-TYPE
    SYNTAX       SnmpAdminString
    MAX-ACCESS   read-only
    STATUS       current
    DESCRIPTION
        "Cisco Firepower equipment:SwitchIOCardCapProvider:rn
        managed object property"
    ::= { cfprEquipmentSwitchIOCardCapProviderEntry 3 }

cfprEquipmentSwitchIOCardCapProviderDeleted OBJECT-TYPE
    SYNTAX       TruthValue
    MAX-ACCESS   read-only
    STATUS       current
    DESCRIPTION
        "Cisco Firepower equipment:SwitchIOCardCapProvider:deleted
        managed object property"
    ::= { cfprEquipmentSwitchIOCardCapProviderEntry 4 }

cfprEquipmentSwitchIOCardCapProviderDeprecated OBJECT-TYPE
    SYNTAX       TruthValue
    MAX-ACCESS   read-only
    STATUS       current
    DESCRIPTION
        "Cisco Firepower equipment:SwitchIOCardCapProvider:deprecated
        managed object property"
    ::= { cfprEquipmentSwitchIOCardCapProviderEntry 5 }

cfprEquipmentSwitchIOCardCapProviderElementLoadFailures OBJECT-TYPE
    SYNTAX       Gauge32
    MAX-ACCESS   read-only
    STATUS       current
    DESCRIPTION
        "Cisco Firepower equipment:SwitchIOCardCapProvider:elementLoadFail
        ures managed object property"
    ::= { cfprEquipmentSwitchIOCardCapProviderEntry 6 }

cfprEquipmentSwitchIOCardCapProviderElementsLoaded OBJECT-TYPE
    SYNTAX       Gauge32
    MAX-ACCESS   read-only
    STATUS       current
    DESCRIPTION
        "Cisco Firepower equipment:SwitchIOCardCapProvider:elementsLoaded
        managed object property"
    ::= { cfprEquipmentSwitchIOCardCapProviderEntry 7 }

cfprEquipmentSwitchIOCardCapProviderGencount OBJECT-TYPE
    SYNTAX       Gauge32
    MAX-ACCESS   read-only
    STATUS       current
    DESCRIPTION
        "Cisco Firepower equipment:SwitchIOCardCapProvider:gencount
        managed object property"
    ::= { cfprEquipmentSwitchIOCardCapProviderEntry 8 }

cfprEquipmentSwitchIOCardCapProviderLoadErrors OBJECT-TYPE
    SYNTAX       Gauge32
    MAX-ACCESS   read-only
    STATUS       current
    DESCRIPTION
        "Cisco Firepower equipment:SwitchIOCardCapProvider:loadErrors
        managed object property"
    ::= { cfprEquipmentSwitchIOCardCapProviderEntry 9 }

cfprEquipmentSwitchIOCardCapProviderLoadWarnings OBJECT-TYPE
    SYNTAX       Gauge32
    MAX-ACCESS   read-only
    STATUS       current
    DESCRIPTION
        "Cisco Firepower equipment:SwitchIOCardCapProvider:loadWarnings
        managed object property"
    ::= { cfprEquipmentSwitchIOCardCapProviderEntry 10 }

cfprEquipmentSwitchIOCardCapProviderMgmtPlaneVer OBJECT-TYPE
    SYNTAX       SnmpAdminString
    MAX-ACCESS   read-only
    STATUS       current
    DESCRIPTION
        "Cisco Firepower equipment:SwitchIOCardCapProvider:mgmtPlaneVer
        managed object property"
    ::= { cfprEquipmentSwitchIOCardCapProviderEntry 11 }

cfprEquipmentSwitchIOCardCapProviderModel OBJECT-TYPE
    SYNTAX       SnmpAdminString
    MAX-ACCESS   read-only
    STATUS       current
    DESCRIPTION
        "Cisco Firepower equipment:SwitchIOCardCapProvider:model
        managed object property"
    ::= { cfprEquipmentSwitchIOCardCapProviderEntry 12 }

cfprEquipmentSwitchIOCardCapProviderPromCardType OBJECT-TYPE
    SYNTAX       Gauge32
    MAX-ACCESS   read-only
    STATUS       current
    DESCRIPTION
        "Cisco Firepower equipment:SwitchIOCardCapProvider:promCardType
        managed object property"
    ::= { cfprEquipmentSwitchIOCardCapProviderEntry 13 }

cfprEquipmentSwitchIOCardCapProviderRevision OBJECT-TYPE
    SYNTAX       SnmpAdminString
    MAX-ACCESS   read-only
    STATUS       current
    DESCRIPTION
        "Cisco Firepower equipment:SwitchIOCardCapProvider:revision
        managed object property"
    ::= { cfprEquipmentSwitchIOCardCapProviderEntry 14 }

cfprEquipmentSwitchIOCardCapProviderVendor OBJECT-TYPE
    SYNTAX       SnmpAdminString
    MAX-ACCESS   read-only
    STATUS       current
    DESCRIPTION
        "Cisco Firepower equipment:SwitchIOCardCapProvider:vendor
        managed object property"
    ::= { cfprEquipmentSwitchIOCardCapProviderEntry 15 }

cfprEquipmentSwitchIOCardFsmTable OBJECT-TYPE
    SYNTAX           SEQUENCE OF CfprEquipmentSwitchIOCardFsmEntry
    MAX-ACCESS       not-accessible
    STATUS           current
    DESCRIPTION
        "Cisco Firepower equipment:SwitchIOCardFsm managed object table"
    ::= { cfprEquipmentObjects 136 }

cfprEquipmentSwitchIOCardFsmEntry OBJECT-TYPE
    SYNTAX           CfprEquipmentSwitchIOCardFsmEntry
    MAX-ACCESS       not-accessible
    STATUS           current
    DESCRIPTION
        "Entry for the cfprEquipmentSwitchIOCardFsmTable table."
    INDEX { cfprEquipmentSwitchIOCardFsmInstanceId }
    ::= { cfprEquipmentSwitchIOCardFsmTable 1 }

CfprEquipmentSwitchIOCardFsmEntry ::= SEQUENCE {
    cfprEquipmentSwitchIOCardFsmInstanceId                           CfprManagedObjectId,
    cfprEquipmentSwitchIOCardFsmDn                                   CfprManagedObjectDn,
    cfprEquipmentSwitchIOCardFsmRn                                   SnmpAdminString,
    cfprEquipmentSwitchIOCardFsmCompletionTime                       DateAndTime,
    cfprEquipmentSwitchIOCardFsmCurrentFsm                           CfprEquipmentSwitchIOCardFsmCurrentFsm,
    cfprEquipmentSwitchIOCardFsmDescrData                            SnmpAdminString,
    cfprEquipmentSwitchIOCardFsmFsmStatus                            CfprFsmFsmStageStatus,
    cfprEquipmentSwitchIOCardFsmProgress                             Gauge32,
    cfprEquipmentSwitchIOCardFsmRmtErrCode                           Gauge32,
    cfprEquipmentSwitchIOCardFsmRmtErrDescr                          SnmpAdminString,
    cfprEquipmentSwitchIOCardFsmRmtRslt                              CfprConditionRemoteInvRslt
}

cfprEquipmentSwitchIOCardFsmInstanceId OBJECT-TYPE
    SYNTAX       CfprManagedObjectId
    MAX-ACCESS   not-accessible
    STATUS       current
    DESCRIPTION
        "Instance identifier of the managed object."
    ::= { cfprEquipmentSwitchIOCardFsmEntry 1 }

cfprEquipmentSwitchIOCardFsmDn OBJECT-TYPE
    SYNTAX       CfprManagedObjectDn
    MAX-ACCESS   read-only
    STATUS       current
    DESCRIPTION
        "Cisco Firepower equipment:SwitchIOCardFsm:dn managed
        object property"
    ::= { cfprEquipmentSwitchIOCardFsmEntry 2 }

cfprEquipmentSwitchIOCardFsmRn OBJECT-TYPE
    SYNTAX       SnmpAdminString
    MAX-ACCESS   read-only
    STATUS       current
    DESCRIPTION
        "Cisco Firepower equipment:SwitchIOCardFsm:rn managed
        object property"
    ::= { cfprEquipmentSwitchIOCardFsmEntry 3 }

cfprEquipmentSwitchIOCardFsmCompletionTime OBJECT-TYPE
    SYNTAX       DateAndTime
    MAX-ACCESS   read-only
    STATUS       current
    DESCRIPTION
        "Cisco Firepower equipment:SwitchIOCardFsm:completionTime
        managed object property"
    ::= { cfprEquipmentSwitchIOCardFsmEntry 4 }

cfprEquipmentSwitchIOCardFsmCurrentFsm OBJECT-TYPE
    SYNTAX       CfprEquipmentSwitchIOCardFsmCurrentFsm
    MAX-ACCESS   read-only
    STATUS       current
    DESCRIPTION
        "Cisco Firepower equipment:SwitchIOCardFsm:currentFsm
        managed object property"
    ::= { cfprEquipmentSwitchIOCardFsmEntry 5 }

cfprEquipmentSwitchIOCardFsmDescrData OBJECT-TYPE
    SYNTAX       SnmpAdminString
    MAX-ACCESS   read-only
    STATUS       current
    DESCRIPTION
        "Cisco Firepower equipment:SwitchIOCardFsm:descr
        managed object property"
    ::= { cfprEquipmentSwitchIOCardFsmEntry 6 }

cfprEquipmentSwitchIOCardFsmFsmStatus OBJECT-TYPE
    SYNTAX       CfprFsmFsmStageStatus
    MAX-ACCESS   read-only
    STATUS       current
    DESCRIPTION
        "Cisco Firepower equipment:SwitchIOCardFsm:fsmStatus
        managed object property"
    ::= { cfprEquipmentSwitchIOCardFsmEntry 7 }

cfprEquipmentSwitchIOCardFsmProgress OBJECT-TYPE
    SYNTAX       Gauge32
    MAX-ACCESS   read-only
    STATUS       current
    DESCRIPTION
        "Cisco Firepower equipment:SwitchIOCardFsm:progress
        managed object property"
    ::= { cfprEquipmentSwitchIOCardFsmEntry 8 }

cfprEquipmentSwitchIOCardFsmRmtErrCode OBJECT-TYPE
    SYNTAX       Gauge32
    MAX-ACCESS   read-only
    STATUS       current
    DESCRIPTION
        "Cisco Firepower equipment:SwitchIOCardFsm:rmtErrCode
        managed object property"
    ::= { cfprEquipmentSwitchIOCardFsmEntry 9 }

cfprEquipmentSwitchIOCardFsmRmtErrDescr OBJECT-TYPE
    SYNTAX       SnmpAdminString
    MAX-ACCESS   read-only
    STATUS       current
    DESCRIPTION
        "Cisco Firepower equipment:SwitchIOCardFsm:rmtErrDescr
        managed object property"
    ::= { cfprEquipmentSwitchIOCardFsmEntry 10 }

cfprEquipmentSwitchIOCardFsmRmtRslt OBJECT-TYPE
    SYNTAX       CfprConditionRemoteInvRslt
    MAX-ACCESS   read-only
    STATUS       current
    DESCRIPTION
        "Cisco Firepower equipment:SwitchIOCardFsm:rmtRslt
        managed object property"
    ::= { cfprEquipmentSwitchIOCardFsmEntry 11 }

cfprEquipmentSwitchIOCardFsmStageTable OBJECT-TYPE
    SYNTAX           SEQUENCE OF CfprEquipmentSwitchIOCardFsmStageEntry
    MAX-ACCESS       not-accessible
    STATUS           current
    DESCRIPTION
        "Cisco Firepower equipment:SwitchIOCardFsmStage
        managed object table"
    ::= { cfprEquipmentObjects 137 }

cfprEquipmentSwitchIOCardFsmStageEntry OBJECT-TYPE
    SYNTAX           CfprEquipmentSwitchIOCardFsmStageEntry
    MAX-ACCESS       not-accessible
    STATUS           current
    DESCRIPTION
        "Entry for the cfprEquipmentSwitchIOCardFsmStageTable table."
    INDEX { cfprEquipmentSwitchIOCardFsmStageInstanceId }
    ::= { cfprEquipmentSwitchIOCardFsmStageTable 1 }

CfprEquipmentSwitchIOCardFsmStageEntry ::= SEQUENCE {
    cfprEquipmentSwitchIOCardFsmStageInstanceId                      CfprManagedObjectId,
    cfprEquipmentSwitchIOCardFsmStageDn                              CfprManagedObjectDn,
    cfprEquipmentSwitchIOCardFsmStageRn                              SnmpAdminString,
    cfprEquipmentSwitchIOCardFsmStageDescrData                       SnmpAdminString,
    cfprEquipmentSwitchIOCardFsmStageLastUpdateTime                  DateAndTime,
    cfprEquipmentSwitchIOCardFsmStageName                            CfprEquipmentSwitchIOCardFsmStageName,
    cfprEquipmentSwitchIOCardFsmStageOrder                           Gauge32,
    cfprEquipmentSwitchIOCardFsmStageRetry                           Gauge32,
    cfprEquipmentSwitchIOCardFsmStageStageStatus                     CfprFsmFsmStageStatus
}

cfprEquipmentSwitchIOCardFsmStageInstanceId OBJECT-TYPE
    SYNTAX       CfprManagedObjectId
    MAX-ACCESS   not-accessible
    STATUS       current
    DESCRIPTION
        "Instance identifier of the managed object."
    ::= { cfprEquipmentSwitchIOCardFsmStageEntry 1 }

cfprEquipmentSwitchIOCardFsmStageDn OBJECT-TYPE
    SYNTAX       CfprManagedObjectDn
    MAX-ACCESS   read-only
    STATUS       current
    DESCRIPTION
        "Cisco Firepower equipment:SwitchIOCardFsmStage:dn
        managed object property"
    ::= { cfprEquipmentSwitchIOCardFsmStageEntry 2 }

cfprEquipmentSwitchIOCardFsmStageRn OBJECT-TYPE
    SYNTAX       SnmpAdminString
    MAX-ACCESS   read-only
    STATUS       current
    DESCRIPTION
        "Cisco Firepower equipment:SwitchIOCardFsmStage:rn
        managed object property"
    ::= { cfprEquipmentSwitchIOCardFsmStageEntry 3 }

cfprEquipmentSwitchIOCardFsmStageDescrData OBJECT-TYPE
    SYNTAX       SnmpAdminString
    MAX-ACCESS   read-only
    STATUS       current
    DESCRIPTION
        "Cisco Firepower equipment:SwitchIOCardFsmStage:descr
        managed object property"
    ::= { cfprEquipmentSwitchIOCardFsmStageEntry 4 }

cfprEquipmentSwitchIOCardFsmStageLastUpdateTime OBJECT-TYPE
    SYNTAX       DateAndTime
    MAX-ACCESS   read-only
    STATUS       current
    DESCRIPTION
        "Cisco Firepower equipment:SwitchIOCardFsmStage:lastUpdateTime
        managed object property"
    ::= { cfprEquipmentSwitchIOCardFsmStageEntry 5 }

cfprEquipmentSwitchIOCardFsmStageName OBJECT-TYPE
    SYNTAX       CfprEquipmentSwitchIOCardFsmStageName
    MAX-ACCESS   read-only
    STATUS       current
    DESCRIPTION
        "Cisco Firepower equipment:SwitchIOCardFsmStage:name
        managed object property"
    ::= { cfprEquipmentSwitchIOCardFsmStageEntry 6 }

cfprEquipmentSwitchIOCardFsmStageOrder OBJECT-TYPE
    SYNTAX       Gauge32
    MAX-ACCESS   read-only
    STATUS       current
    DESCRIPTION
        "Cisco Firepower equipment:SwitchIOCardFsmStage:order
        managed object property"
    ::= { cfprEquipmentSwitchIOCardFsmStageEntry 7 }

cfprEquipmentSwitchIOCardFsmStageRetry OBJECT-TYPE
    SYNTAX       Gauge32
    MAX-ACCESS   read-only
    STATUS       current
    DESCRIPTION
        "Cisco Firepower equipment:SwitchIOCardFsmStage:retry
        managed object property"
    ::= { cfprEquipmentSwitchIOCardFsmStageEntry 8 }

cfprEquipmentSwitchIOCardFsmStageStageStatus OBJECT-TYPE
    SYNTAX       CfprFsmFsmStageStatus
    MAX-ACCESS   read-only
    STATUS       current
    DESCRIPTION
        "Cisco Firepower equipment:SwitchIOCardFsmStage:stageStatus
        managed object property"
    ::= { cfprEquipmentSwitchIOCardFsmStageEntry 9 }

cfprEquipmentSwitchTypeDefTable OBJECT-TYPE
    SYNTAX           SEQUENCE OF CfprEquipmentSwitchTypeDefEntry
    MAX-ACCESS       not-accessible
    STATUS           current
    DESCRIPTION
        "Cisco Firepower equipment:SwitchTypeDef managed object table"
    ::= { cfprEquipmentObjects 138 }

cfprEquipmentSwitchTypeDefEntry OBJECT-TYPE
    SYNTAX           CfprEquipmentSwitchTypeDefEntry
    MAX-ACCESS       not-accessible
    STATUS           current
    DESCRIPTION
        "Entry for the cfprEquipmentSwitchTypeDefTable table."
    INDEX { cfprEquipmentSwitchTypeDefInstanceId }
    ::= { cfprEquipmentSwitchTypeDefTable 1 }

CfprEquipmentSwitchTypeDefEntry ::= SEQUENCE {
    cfprEquipmentSwitchTypeDefInstanceId                             CfprManagedObjectId,
    cfprEquipmentSwitchTypeDefDn                                     CfprManagedObjectDn,
    cfprEquipmentSwitchTypeDefRn                                     SnmpAdminString,
    cfprEquipmentSwitchTypeDefDescr                                  SnmpAdminString,
    cfprEquipmentSwitchTypeDefIntId                                  SnmpAdminString,
    cfprEquipmentSwitchTypeDefName                                   SnmpAdminString,
    cfprEquipmentSwitchTypeDefPolicyLevel                            Gauge32,
    cfprEquipmentSwitchTypeDefPolicyOwner                            CfprPolicyPolicyOwner,
    cfprEquipmentSwitchTypeDefType                                   SnmpAdminString
}

cfprEquipmentSwitchTypeDefInstanceId OBJECT-TYPE
    SYNTAX       CfprManagedObjectId
    MAX-ACCESS   not-accessible
    STATUS       current
    DESCRIPTION
        "Instance identifier of the managed object."
    ::= { cfprEquipmentSwitchTypeDefEntry 1 }

cfprEquipmentSwitchTypeDefDn OBJECT-TYPE
    SYNTAX       CfprManagedObjectDn
    MAX-ACCESS   read-only
    STATUS       current
    DESCRIPTION
        "Cisco Firepower equipment:SwitchTypeDef:dn managed
        object property"
    ::= { cfprEquipmentSwitchTypeDefEntry 2 }

cfprEquipmentSwitchTypeDefRn OBJECT-TYPE
    SYNTAX       SnmpAdminString
    MAX-ACCESS   read-only
    STATUS       current
    DESCRIPTION
        "Cisco Firepower equipment:SwitchTypeDef:rn managed
        object property"
    ::= { cfprEquipmentSwitchTypeDefEntry 3 }

cfprEquipmentSwitchTypeDefDescr OBJECT-TYPE
    SYNTAX       SnmpAdminString
    MAX-ACCESS   read-only
    STATUS       current
    DESCRIPTION
        "Cisco Firepower equipment:SwitchTypeDef:descr
        managed object property"
    ::= { cfprEquipmentSwitchTypeDefEntry 4 }

cfprEquipmentSwitchTypeDefIntId OBJECT-TYPE
    SYNTAX       SnmpAdminString
    MAX-ACCESS   read-only
    STATUS       current
    DESCRIPTION
        "Cisco Firepower equipment:SwitchTypeDef:intId
        managed object property"
    ::= { cfprEquipmentSwitchTypeDefEntry 5 }

cfprEquipmentSwitchTypeDefName OBJECT-TYPE
    SYNTAX       SnmpAdminString
    MAX-ACCESS   read-only
    STATUS       current
    DESCRIPTION
        "Cisco Firepower equipment:SwitchTypeDef:name managed
        object property"
    ::= { cfprEquipmentSwitchTypeDefEntry 6 }

cfprEquipmentSwitchTypeDefPolicyLevel OBJECT-TYPE
    SYNTAX       Gauge32
    MAX-ACCESS   read-only
    STATUS       current
    DESCRIPTION
        "Cisco Firepower equipment:SwitchTypeDef:policyLevel
        managed object property"
    ::= { cfprEquipmentSwitchTypeDefEntry 7 }

cfprEquipmentSwitchTypeDefPolicyOwner OBJECT-TYPE
    SYNTAX       CfprPolicyPolicyOwner
    MAX-ACCESS   read-only
    STATUS       current
    DESCRIPTION
        "Cisco Firepower equipment:SwitchTypeDef:policyOwner
        managed object property"
    ::= { cfprEquipmentSwitchTypeDefEntry 8 }

cfprEquipmentSwitchTypeDefType OBJECT-TYPE
    SYNTAX       SnmpAdminString
    MAX-ACCESS   read-only
    STATUS       current
    DESCRIPTION
        "Cisco Firepower equipment:SwitchTypeDef:type managed
        object property"
    ::= { cfprEquipmentSwitchTypeDefEntry 9 }

cfprEquipmentTpmTable OBJECT-TYPE
    SYNTAX           SEQUENCE OF CfprEquipmentTpmEntry
    MAX-ACCESS       not-accessible
    STATUS           current
    DESCRIPTION
        "Cisco Firepower equipment:Tpm managed object table"
    ::= { cfprEquipmentObjects 139 }

cfprEquipmentTpmEntry OBJECT-TYPE
    SYNTAX           CfprEquipmentTpmEntry
    MAX-ACCESS       not-accessible
    STATUS           current
    DESCRIPTION
        "Entry for the cfprEquipmentTpmTable table."
    INDEX { cfprEquipmentTpmInstanceId }
    ::= { cfprEquipmentTpmTable 1 }

CfprEquipmentTpmEntry ::= SEQUENCE {
    cfprEquipmentTpmInstanceId                                       CfprManagedObjectId,
    cfprEquipmentTpmDn                                               CfprManagedObjectDn,
    cfprEquipmentTpmRn                                               SnmpAdminString,
    cfprEquipmentTpmActiveStatus                                     CfprEquipmentActiveStatus,
    cfprEquipmentTpmEnabledStatus                                    CfprEquipmentEnabledStatus,
    cfprEquipmentTpmId                                               Gauge32,
    cfprEquipmentTpmModel                                            SnmpAdminString,
    cfprEquipmentTpmOwnership                                        CfprEquipmentOwnership,
    cfprEquipmentTpmPasswordState                                    CfprEquipmentPasswordState,
    cfprEquipmentTpmPresence                                         CfprEquipmentPresence,
    cfprEquipmentTpmRevision                                         SnmpAdminString,
    cfprEquipmentTpmSerial                                           SnmpAdminString,
    cfprEquipmentTpmTpmRevision                                      Gauge32,
    cfprEquipmentTpmType                                             CfprEquipmentTpmType,
    cfprEquipmentTpmVendor                                           SnmpAdminString
}

cfprEquipmentTpmInstanceId OBJECT-TYPE
    SYNTAX       CfprManagedObjectId
    MAX-ACCESS   not-accessible
    STATUS       current
    DESCRIPTION
        "Instance identifier of the managed object."
    ::= { cfprEquipmentTpmEntry 1 }

cfprEquipmentTpmDn OBJECT-TYPE
    SYNTAX       CfprManagedObjectDn
    MAX-ACCESS   read-only
    STATUS       current
    DESCRIPTION
        "Cisco Firepower equipment:Tpm:dn managed object property"
    ::= { cfprEquipmentTpmEntry 2 }

cfprEquipmentTpmRn OBJECT-TYPE
    SYNTAX       SnmpAdminString
    MAX-ACCESS   read-only
    STATUS       current
    DESCRIPTION
        "Cisco Firepower equipment:Tpm:rn managed object property"
    ::= { cfprEquipmentTpmEntry 3 }

cfprEquipmentTpmActiveStatus OBJECT-TYPE
    SYNTAX       CfprEquipmentActiveStatus
    MAX-ACCESS   read-only
    STATUS       current
    DESCRIPTION
        "Cisco Firepower equipment:Tpm:activeStatus managed
        object property"
    ::= { cfprEquipmentTpmEntry 4 }

cfprEquipmentTpmEnabledStatus OBJECT-TYPE
    SYNTAX       CfprEquipmentEnabledStatus
    MAX-ACCESS   read-only
    STATUS       current
    DESCRIPTION
        "Cisco Firepower equipment:Tpm:enabledStatus managed
        object property"
    ::= { cfprEquipmentTpmEntry 5 }

cfprEquipmentTpmId OBJECT-TYPE
    SYNTAX       Gauge32
    MAX-ACCESS   read-only
    STATUS       current
    DESCRIPTION
        "Cisco Firepower equipment:Tpm:id managed object property"
    ::= { cfprEquipmentTpmEntry 6 }

cfprEquipmentTpmModel OBJECT-TYPE
    SYNTAX       SnmpAdminString
    MAX-ACCESS   read-only
    STATUS       current
    DESCRIPTION
        "Cisco Firepower equipment:Tpm:model managed object property"
    ::= { cfprEquipmentTpmEntry 7 }

cfprEquipmentTpmOwnership OBJECT-TYPE
    SYNTAX       CfprEquipmentOwnership
    MAX-ACCESS   read-only
    STATUS       current
    DESCRIPTION
        "Cisco Firepower equipment:Tpm:ownership managed object property"
    ::= { cfprEquipmentTpmEntry 8 }

cfprEquipmentTpmPasswordState OBJECT-TYPE
    SYNTAX       CfprEquipmentPasswordState
    MAX-ACCESS   read-only
    STATUS       current
    DESCRIPTION
        "Cisco Firepower equipment:Tpm:passwordState managed
        object property"
    ::= { cfprEquipmentTpmEntry 9 }

cfprEquipmentTpmPresence OBJECT-TYPE
    SYNTAX       CfprEquipmentPresence
    MAX-ACCESS   read-only
    STATUS       current
    DESCRIPTION
        "Cisco Firepower equipment:Tpm:presence managed object property"
    ::= { cfprEquipmentTpmEntry 10 }

cfprEquipmentTpmRevision OBJECT-TYPE
    SYNTAX       SnmpAdminString
    MAX-ACCESS   read-only
    STATUS       current
    DESCRIPTION
        "Cisco Firepower equipment:Tpm:revision managed object property"
    ::= { cfprEquipmentTpmEntry 11 }

cfprEquipmentTpmSerial OBJECT-TYPE
    SYNTAX       SnmpAdminString
    MAX-ACCESS   read-only
    STATUS       current
    DESCRIPTION
        "Cisco Firepower equipment:Tpm:serial managed object property"
    ::= { cfprEquipmentTpmEntry 12 }

cfprEquipmentTpmTpmRevision OBJECT-TYPE
    SYNTAX       Gauge32
    MAX-ACCESS   read-only
    STATUS       current
    DESCRIPTION
        "Cisco Firepower equipment:Tpm:tpmRevision managed
        object property"
    ::= { cfprEquipmentTpmEntry 13 }

cfprEquipmentTpmType OBJECT-TYPE
    SYNTAX       CfprEquipmentTpmType
    MAX-ACCESS   read-only
    STATUS       current
    DESCRIPTION
        "Cisco Firepower equipment:Tpm:type managed object property"
    ::= { cfprEquipmentTpmEntry 14 }

cfprEquipmentTpmVendor OBJECT-TYPE
    SYNTAX       SnmpAdminString
    MAX-ACCESS   read-only
    STATUS       current
    DESCRIPTION
        "Cisco Firepower equipment:Tpm:vendor managed object property"
    ::= { cfprEquipmentTpmEntry 15 }

cfprEquipmentTpmCapProviderTable OBJECT-TYPE
    SYNTAX           SEQUENCE OF CfprEquipmentTpmCapProviderEntry
    MAX-ACCESS       not-accessible
    STATUS           current
    DESCRIPTION
        "Cisco Firepower equipment:TpmCapProvider managed object table"
    ::= { cfprEquipmentObjects 140 }

cfprEquipmentTpmCapProviderEntry OBJECT-TYPE
    SYNTAX           CfprEquipmentTpmCapProviderEntry
    MAX-ACCESS       not-accessible
    STATUS           current
    DESCRIPTION
        "Entry for the cfprEquipmentTpmCapProviderTable table."
    INDEX { cfprEquipmentTpmCapProviderInstanceId }
    ::= { cfprEquipmentTpmCapProviderTable 1 }

CfprEquipmentTpmCapProviderEntry ::= SEQUENCE {
    cfprEquipmentTpmCapProviderInstanceId                            CfprManagedObjectId,
    cfprEquipmentTpmCapProviderDn                                    CfprManagedObjectDn,
    cfprEquipmentTpmCapProviderRn                                    SnmpAdminString,
    cfprEquipmentTpmCapProviderDeleted                               TruthValue,
    cfprEquipmentTpmCapProviderDeprecated                            TruthValue,
    cfprEquipmentTpmCapProviderElementLoadFailures                   Gauge32,
    cfprEquipmentTpmCapProviderElementsLoaded                        Gauge32,
    cfprEquipmentTpmCapProviderGencount                              Gauge32,
    cfprEquipmentTpmCapProviderLoadErrors                            Gauge32,
    cfprEquipmentTpmCapProviderLoadWarnings                          Gauge32,
    cfprEquipmentTpmCapProviderMgmtPlaneVer                          SnmpAdminString,
    cfprEquipmentTpmCapProviderModel                                 SnmpAdminString,
    cfprEquipmentTpmCapProviderPromCardType                          Gauge32,
    cfprEquipmentTpmCapProviderRevision                              SnmpAdminString,
    cfprEquipmentTpmCapProviderVendor                                SnmpAdminString
}

cfprEquipmentTpmCapProviderInstanceId OBJECT-TYPE
    SYNTAX       CfprManagedObjectId
    MAX-ACCESS   not-accessible
    STATUS       current
    DESCRIPTION
        "Instance identifier of the managed object."
    ::= { cfprEquipmentTpmCapProviderEntry 1 }

cfprEquipmentTpmCapProviderDn OBJECT-TYPE
    SYNTAX       CfprManagedObjectDn
    MAX-ACCESS   read-only
    STATUS       current
    DESCRIPTION
        "Cisco Firepower equipment:TpmCapProvider:dn managed
        object property"
    ::= { cfprEquipmentTpmCapProviderEntry 2 }

cfprEquipmentTpmCapProviderRn OBJECT-TYPE
    SYNTAX       SnmpAdminString
    MAX-ACCESS   read-only
    STATUS       current
    DESCRIPTION
        "Cisco Firepower equipment:TpmCapProvider:rn managed
        object property"
    ::= { cfprEquipmentTpmCapProviderEntry 3 }

cfprEquipmentTpmCapProviderDeleted OBJECT-TYPE
    SYNTAX       TruthValue
    MAX-ACCESS   read-only
    STATUS       current
    DESCRIPTION
        "Cisco Firepower equipment:TpmCapProvider:deleted
        managed object property"
    ::= { cfprEquipmentTpmCapProviderEntry 4 }

cfprEquipmentTpmCapProviderDeprecated OBJECT-TYPE
    SYNTAX       TruthValue
    MAX-ACCESS   read-only
    STATUS       current
    DESCRIPTION
        "Cisco Firepower equipment:TpmCapProvider:deprecated
        managed object property"
    ::= { cfprEquipmentTpmCapProviderEntry 5 }

cfprEquipmentTpmCapProviderElementLoadFailures OBJECT-TYPE
    SYNTAX       Gauge32
    MAX-ACCESS   read-only
    STATUS       current
    DESCRIPTION
        "Cisco Firepower equipment:TpmCapProvider:elementLoadFailures
        managed object property"
    ::= { cfprEquipmentTpmCapProviderEntry 6 }

cfprEquipmentTpmCapProviderElementsLoaded OBJECT-TYPE
    SYNTAX       Gauge32
    MAX-ACCESS   read-only
    STATUS       current
    DESCRIPTION
        "Cisco Firepower equipment:TpmCapProvider:elementsLoaded
        managed object property"
    ::= { cfprEquipmentTpmCapProviderEntry 7 }

cfprEquipmentTpmCapProviderGencount OBJECT-TYPE
    SYNTAX       Gauge32
    MAX-ACCESS   read-only
    STATUS       current
    DESCRIPTION
        "Cisco Firepower equipment:TpmCapProvider:gencount
        managed object property"
    ::= { cfprEquipmentTpmCapProviderEntry 8 }

cfprEquipmentTpmCapProviderLoadErrors OBJECT-TYPE
    SYNTAX       Gauge32
    MAX-ACCESS   read-only
    STATUS       current
    DESCRIPTION
        "Cisco Firepower equipment:TpmCapProvider:loadErrors
        managed object property"
    ::= { cfprEquipmentTpmCapProviderEntry 9 }

cfprEquipmentTpmCapProviderLoadWarnings OBJECT-TYPE
    SYNTAX       Gauge32
    MAX-ACCESS   read-only
    STATUS       current
    DESCRIPTION
        "Cisco Firepower equipment:TpmCapProvider:loadWarnings
        managed object property"
    ::= { cfprEquipmentTpmCapProviderEntry 10 }

cfprEquipmentTpmCapProviderMgmtPlaneVer OBJECT-TYPE
    SYNTAX       SnmpAdminString
    MAX-ACCESS   read-only
    STATUS       current
    DESCRIPTION
        "Cisco Firepower equipment:TpmCapProvider:mgmtPlaneVer
        managed object property"
    ::= { cfprEquipmentTpmCapProviderEntry 11 }

cfprEquipmentTpmCapProviderModel OBJECT-TYPE
    SYNTAX       SnmpAdminString
    MAX-ACCESS   read-only
    STATUS       current
    DESCRIPTION
        "Cisco Firepower equipment:TpmCapProvider:model
        managed object property"
    ::= { cfprEquipmentTpmCapProviderEntry 12 }

cfprEquipmentTpmCapProviderPromCardType OBJECT-TYPE
    SYNTAX       Gauge32
    MAX-ACCESS   read-only
    STATUS       current
    DESCRIPTION
        "Cisco Firepower equipment:TpmCapProvider:promCardType
        managed object property"
    ::= { cfprEquipmentTpmCapProviderEntry 13 }

cfprEquipmentTpmCapProviderRevision OBJECT-TYPE
    SYNTAX       SnmpAdminString
    MAX-ACCESS   read-only
    STATUS       current
    DESCRIPTION
        "Cisco Firepower equipment:TpmCapProvider:revision
        managed object property"
    ::= { cfprEquipmentTpmCapProviderEntry 14 }

cfprEquipmentTpmCapProviderVendor OBJECT-TYPE
    SYNTAX       SnmpAdminString
    MAX-ACCESS   read-only
    STATUS       current
    DESCRIPTION
        "Cisco Firepower equipment:TpmCapProvider:vendor
        managed object property"
    ::= { cfprEquipmentTpmCapProviderEntry 15 }

cfprEquipmentUnifiedPortCapProviderTable OBJECT-TYPE
    SYNTAX           SEQUENCE OF CfprEquipmentUnifiedPortCapProviderEntry
    MAX-ACCESS       not-accessible
    STATUS           current
    DESCRIPTION
        "Cisco Firepower equipment:UnifiedPortCapProvider
        managed object table"
    ::= { cfprEquipmentObjects 141 }

cfprEquipmentUnifiedPortCapProviderEntry OBJECT-TYPE
    SYNTAX           CfprEquipmentUnifiedPortCapProviderEntry
    MAX-ACCESS       not-accessible
    STATUS           current
    DESCRIPTION
        "Entry for the cfprEquipmentUnifiedPortCapProviderTable table."
    INDEX { cfprEquipmentUnifiedPortCapProviderInstanceId }
    ::= { cfprEquipmentUnifiedPortCapProviderTable 1 }

CfprEquipmentUnifiedPortCapProviderEntry ::= SEQUENCE {
    cfprEquipmentUnifiedPortCapProviderInstanceId                    CfprManagedObjectId,
    cfprEquipmentUnifiedPortCapProviderDn                            CfprManagedObjectDn,
    cfprEquipmentUnifiedPortCapProviderRn                            SnmpAdminString,
    cfprEquipmentUnifiedPortCapProviderDescr                         SnmpAdminString,
    cfprEquipmentUnifiedPortCapProviderEndPortId                     Gauge32,
    cfprEquipmentUnifiedPortCapProviderIntId                         SnmpAdminString,
    cfprEquipmentUnifiedPortCapProviderName                          SnmpAdminString,
    cfprEquipmentUnifiedPortCapProviderPolicyLevel                   Gauge32,
    cfprEquipmentUnifiedPortCapProviderPolicyOwner                   CfprPolicyPolicyOwner,
    cfprEquipmentUnifiedPortCapProviderStartPortId                   Gauge32,
    cfprEquipmentUnifiedPortCapProviderSupportedAlgorithm            CfprEquipmentUnifiedPortAlgorithm
}

cfprEquipmentUnifiedPortCapProviderInstanceId OBJECT-TYPE
    SYNTAX       CfprManagedObjectId
    MAX-ACCESS   not-accessible
    STATUS       current
    DESCRIPTION
        "Instance identifier of the managed object."
    ::= { cfprEquipmentUnifiedPortCapProviderEntry 1 }

cfprEquipmentUnifiedPortCapProviderDn OBJECT-TYPE
    SYNTAX       CfprManagedObjectDn
    MAX-ACCESS   read-only
    STATUS       current
    DESCRIPTION
        "Cisco Firepower equipment:UnifiedPortCapProvider:dn
        managed object property"
    ::= { cfprEquipmentUnifiedPortCapProviderEntry 2 }

cfprEquipmentUnifiedPortCapProviderRn OBJECT-TYPE
    SYNTAX       SnmpAdminString
    MAX-ACCESS   read-only
    STATUS       current
    DESCRIPTION
        "Cisco Firepower equipment:UnifiedPortCapProvider:rn
        managed object property"
    ::= { cfprEquipmentUnifiedPortCapProviderEntry 3 }

cfprEquipmentUnifiedPortCapProviderDescr OBJECT-TYPE
    SYNTAX       SnmpAdminString
    MAX-ACCESS   read-only
    STATUS       current
    DESCRIPTION
        "Cisco Firepower equipment:UnifiedPortCapProvider:descr
        managed object property"
    ::= { cfprEquipmentUnifiedPortCapProviderEntry 4 }

cfprEquipmentUnifiedPortCapProviderEndPortId OBJECT-TYPE
    SYNTAX       Gauge32
    MAX-ACCESS   read-only
    STATUS       current
    DESCRIPTION
        "Cisco Firepower equipment:UnifiedPortCapProvider:endPortId
        managed object property"
    ::= { cfprEquipmentUnifiedPortCapProviderEntry 5 }

cfprEquipmentUnifiedPortCapProviderIntId OBJECT-TYPE
    SYNTAX       SnmpAdminString
    MAX-ACCESS   read-only
    STATUS       current
    DESCRIPTION
        "Cisco Firepower equipment:UnifiedPortCapProvider:intId
        managed object property"
    ::= { cfprEquipmentUnifiedPortCapProviderEntry 6 }

cfprEquipmentUnifiedPortCapProviderName OBJECT-TYPE
    SYNTAX       SnmpAdminString
    MAX-ACCESS   read-only
    STATUS       current
    DESCRIPTION
        "Cisco Firepower equipment:UnifiedPortCapProvider:name
        managed object property"
    ::= { cfprEquipmentUnifiedPortCapProviderEntry 7 }

cfprEquipmentUnifiedPortCapProviderPolicyLevel OBJECT-TYPE
    SYNTAX       Gauge32
    MAX-ACCESS   read-only
    STATUS       current
    DESCRIPTION
        "Cisco Firepower equipment:UnifiedPortCapProvider:policyLevel
        managed object property"
    ::= { cfprEquipmentUnifiedPortCapProviderEntry 8 }

cfprEquipmentUnifiedPortCapProviderPolicyOwner OBJECT-TYPE
    SYNTAX       CfprPolicyPolicyOwner
    MAX-ACCESS   read-only
    STATUS       current
    DESCRIPTION
        "Cisco Firepower equipment:UnifiedPortCapProvider:policyOwner
        managed object property"
    ::= { cfprEquipmentUnifiedPortCapProviderEntry 9 }

cfprEquipmentUnifiedPortCapProviderStartPortId OBJECT-TYPE
    SYNTAX       Gauge32
    MAX-ACCESS   read-only
    STATUS       current
    DESCRIPTION
        "Cisco Firepower equipment:UnifiedPortCapProvider:startPortId
        managed object property"
    ::= { cfprEquipmentUnifiedPortCapProviderEntry 10 }

cfprEquipmentUnifiedPortCapProviderSupportedAlgorithm OBJECT-TYPE
    SYNTAX       CfprEquipmentUnifiedPortAlgorithm
    MAX-ACCESS   read-only
    STATUS       current
    DESCRIPTION
        "Cisco Firepower equipment:UnifiedPortCapProvider:supportedAlgorit
        hm managed object property"
    ::= { cfprEquipmentUnifiedPortCapProviderEntry 11 }

cfprEquipmentUuidFeatureCapTable OBJECT-TYPE
    SYNTAX           SEQUENCE OF CfprEquipmentUuidFeatureCapEntry
    MAX-ACCESS       not-accessible
    STATUS           current
    DESCRIPTION
        "Cisco Firepower equipment:UuidFeatureCap managed object table"
    ::= { cfprEquipmentObjects 142 }

cfprEquipmentUuidFeatureCapEntry OBJECT-TYPE
    SYNTAX           CfprEquipmentUuidFeatureCapEntry
    MAX-ACCESS       not-accessible
    STATUS           current
    DESCRIPTION
        "Entry for the cfprEquipmentUuidFeatureCapTable table."
    INDEX { cfprEquipmentUuidFeatureCapInstanceId }
    ::= { cfprEquipmentUuidFeatureCapTable 1 }

CfprEquipmentUuidFeatureCapEntry ::= SEQUENCE {
    cfprEquipmentUuidFeatureCapInstanceId                            CfprManagedObjectId,
    cfprEquipmentUuidFeatureCapDn                                    CfprManagedObjectDn,
    cfprEquipmentUuidFeatureCapRn                                    SnmpAdminString,
    cfprEquipmentUuidFeatureCapUuidSupportMode                       CfprEquipmentUuidFeatureCapUuidSupportMode
}

cfprEquipmentUuidFeatureCapInstanceId OBJECT-TYPE
    SYNTAX       CfprManagedObjectId
    MAX-ACCESS   not-accessible
    STATUS       current
    DESCRIPTION
        "Instance identifier of the managed object."
    ::= { cfprEquipmentUuidFeatureCapEntry 1 }

cfprEquipmentUuidFeatureCapDn OBJECT-TYPE
    SYNTAX       CfprManagedObjectDn
    MAX-ACCESS   read-only
    STATUS       current
    DESCRIPTION
        "Cisco Firepower equipment:UuidFeatureCap:dn managed
        object property"
    ::= { cfprEquipmentUuidFeatureCapEntry 2 }

cfprEquipmentUuidFeatureCapRn OBJECT-TYPE
    SYNTAX       SnmpAdminString
    MAX-ACCESS   read-only
    STATUS       current
    DESCRIPTION
        "Cisco Firepower equipment:UuidFeatureCap:rn managed
        object property"
    ::= { cfprEquipmentUuidFeatureCapEntry 3 }

cfprEquipmentUuidFeatureCapUuidSupportMode OBJECT-TYPE
    SYNTAX       CfprEquipmentUuidFeatureCapUuidSupportMode
    MAX-ACCESS   read-only
    STATUS       current
    DESCRIPTION
        "Cisco Firepower equipment:UuidFeatureCap:uuidSupportMode
        managed object property"
    ::= { cfprEquipmentUuidFeatureCapEntry 4 }

cfprEquipmentVersionConstraintTable OBJECT-TYPE
    SYNTAX           SEQUENCE OF CfprEquipmentVersionConstraintEntry
    MAX-ACCESS       not-accessible
    STATUS           current
    DESCRIPTION
        "Cisco Firepower equipment:VersionConstraint managed object table"
    ::= { cfprEquipmentObjects 143 }

cfprEquipmentVersionConstraintEntry OBJECT-TYPE
    SYNTAX           CfprEquipmentVersionConstraintEntry
    MAX-ACCESS       not-accessible
    STATUS           current
    DESCRIPTION
        "Entry for the cfprEquipmentVersionConstraintTable table."
    INDEX { cfprEquipmentVersionConstraintInstanceId }
    ::= { cfprEquipmentVersionConstraintTable 1 }

CfprEquipmentVersionConstraintEntry ::= SEQUENCE {
    cfprEquipmentVersionConstraintInstanceId                         CfprManagedObjectId,
    cfprEquipmentVersionConstraintDn                                 CfprManagedObjectDn,
    cfprEquipmentVersionConstraintRn                                 SnmpAdminString,
    cfprEquipmentVersionConstraintMinVer1                            SnmpAdminString
}

cfprEquipmentVersionConstraintInstanceId OBJECT-TYPE
    SYNTAX       CfprManagedObjectId
    MAX-ACCESS   not-accessible
    STATUS       current
    DESCRIPTION
        "Instance identifier of the managed object."
    ::= { cfprEquipmentVersionConstraintEntry 1 }

cfprEquipmentVersionConstraintDn OBJECT-TYPE
    SYNTAX       CfprManagedObjectDn
    MAX-ACCESS   read-only
    STATUS       current
    DESCRIPTION
        "Cisco Firepower equipment:VersionConstraint:dn
        managed object property"
    ::= { cfprEquipmentVersionConstraintEntry 2 }

cfprEquipmentVersionConstraintRn OBJECT-TYPE
    SYNTAX       SnmpAdminString
    MAX-ACCESS   read-only
    STATUS       current
    DESCRIPTION
        "Cisco Firepower equipment:VersionConstraint:rn
        managed object property"
    ::= { cfprEquipmentVersionConstraintEntry 3 }

cfprEquipmentVersionConstraintMinVer1 OBJECT-TYPE
    SYNTAX       SnmpAdminString
    MAX-ACCESS   read-only
    STATUS       current
    DESCRIPTION
        "Cisco Firepower equipment:VersionConstraint:minVer1
        managed object property"
    ::= { cfprEquipmentVersionConstraintEntry 4 }

cfprEquipmentXcvrTable OBJECT-TYPE
    SYNTAX           SEQUENCE OF CfprEquipmentXcvrEntry
    MAX-ACCESS       not-accessible
    STATUS           current
    DESCRIPTION
        "Cisco Firepower equipment:Xcvr managed object table"
    ::= { cfprEquipmentObjects 144 }

cfprEquipmentXcvrEntry OBJECT-TYPE
    SYNTAX           CfprEquipmentXcvrEntry
    MAX-ACCESS       not-accessible
    STATUS           current
    DESCRIPTION
        "Entry for the cfprEquipmentXcvrTable table."
    INDEX { cfprEquipmentXcvrInstanceId }
    ::= { cfprEquipmentXcvrTable 1 }

CfprEquipmentXcvrEntry ::= SEQUENCE {
    cfprEquipmentXcvrInstanceId                                      CfprManagedObjectId,
    cfprEquipmentXcvrDn                                              CfprManagedObjectDn,
    cfprEquipmentXcvrRn                                              SnmpAdminString,
    cfprEquipmentXcvrId                                              CfprEquipmentXcvrId,
    cfprEquipmentXcvrModel                                           SnmpAdminString,
    cfprEquipmentXcvrRevision                                        SnmpAdminString,
    cfprEquipmentXcvrSerial                                          SnmpAdminString,
    cfprEquipmentXcvrTs                                              DateAndTime,
    cfprEquipmentXcvrType                                            CfprEquipmentXcvrType,
    cfprEquipmentXcvrVendor                                          SnmpAdminString,
    cfprEquipmentXcvrState                                           CfprEquipmentXcvrStatus
}

cfprEquipmentXcvrInstanceId OBJECT-TYPE
    SYNTAX       CfprManagedObjectId
    MAX-ACCESS   not-accessible
    STATUS       current
    DESCRIPTION
        "Instance identifier of the managed object."
    ::= { cfprEquipmentXcvrEntry 1 }

cfprEquipmentXcvrDn OBJECT-TYPE
    SYNTAX       CfprManagedObjectDn
    MAX-ACCESS   read-only
    STATUS       current
    DESCRIPTION
        "Cisco Firepower equipment:Xcvr:dn managed object property"
    ::= { cfprEquipmentXcvrEntry 2 }

cfprEquipmentXcvrRn OBJECT-TYPE
    SYNTAX       SnmpAdminString
    MAX-ACCESS   read-only
    STATUS       current
    DESCRIPTION
        "Cisco Firepower equipment:Xcvr:rn managed object property"
    ::= { cfprEquipmentXcvrEntry 3 }

cfprEquipmentXcvrId OBJECT-TYPE
    SYNTAX       CfprEquipmentXcvrId
    MAX-ACCESS   read-only
    STATUS       current
    DESCRIPTION
        "Cisco Firepower equipment:Xcvr:id managed object property"
    ::= { cfprEquipmentXcvrEntry 4 }

cfprEquipmentXcvrModel OBJECT-TYPE
    SYNTAX       SnmpAdminString
    MAX-ACCESS   read-only
    STATUS       current
    DESCRIPTION
        "Cisco Firepower equipment:Xcvr:model managed object property"
    ::= { cfprEquipmentXcvrEntry 5 }

cfprEquipmentXcvrRevision OBJECT-TYPE
    SYNTAX       SnmpAdminString
    MAX-ACCESS   read-only
    STATUS       current
    DESCRIPTION
        "Cisco Firepower equipment:Xcvr:revision managed object property"
    ::= { cfprEquipmentXcvrEntry 6 }

cfprEquipmentXcvrSerial OBJECT-TYPE
    SYNTAX       SnmpAdminString
    MAX-ACCESS   read-only
    STATUS       current
    DESCRIPTION
        "Cisco Firepower equipment:Xcvr:serial managed object property"
    ::= { cfprEquipmentXcvrEntry 7 }

cfprEquipmentXcvrTs OBJECT-TYPE
    SYNTAX       DateAndTime
    MAX-ACCESS   read-only
    STATUS       current
    DESCRIPTION
        "Cisco Firepower equipment:Xcvr:ts managed object property"
    ::= { cfprEquipmentXcvrEntry 8 }

cfprEquipmentXcvrType OBJECT-TYPE
    SYNTAX       CfprEquipmentXcvrType
    MAX-ACCESS   read-only
    STATUS       current
    DESCRIPTION
        "Cisco Firepower equipment:Xcvr:type managed object property"
    ::= { cfprEquipmentXcvrEntry 9 }

cfprEquipmentXcvrVendor OBJECT-TYPE
    SYNTAX       SnmpAdminString
    MAX-ACCESS   read-only
    STATUS       current
    DESCRIPTION
        "Cisco Firepower equipment:Xcvr:vendor managed object property"
    ::= { cfprEquipmentXcvrEntry 10 }

cfprEquipmentXcvrState OBJECT-TYPE
    SYNTAX       CfprEquipmentXcvrStatus
    MAX-ACCESS   read-only
    STATUS       current
    DESCRIPTION
        "Cisco Firepower equipment:Xcvr:state managed object property"
    ::= { cfprEquipmentXcvrEntry 11 }

END
