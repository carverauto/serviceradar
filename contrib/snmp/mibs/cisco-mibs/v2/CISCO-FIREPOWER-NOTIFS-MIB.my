-- ********************************************************************
-- CISCO-FIREPOWER-NOTIFS-MIB.my
-- 
-- Firepower Fault notifications (traps)
--
-- Copyright (c) 2005-2017 Cisco Systems, Inc. All rights reserved.
-- ********************************************************************

CISCO-FIREPOWER-NOTIFS-MIB DEFINITIONS ::= BEGIN

IMPORTS
        MODULE-IDENTITY,
        NOTIFICATION-TYPE
                FROM SNMPv2-SMI
	ciscoMgmt
		FROM CISCO-SMI
        ciscoFirepowerMIB
            FROM CISCO-FIREPOWER-MIB
                cfprFaultInstInstanceId,
                cfprFaultInstDescr,
                cfprFaultInstAffectedObjectId,
                cfprFaultInstAffectedObjectDn,
                cfprFaultInstCreated,
                cfprFaultInstLastTransition,
                cfprFaultInstCode,
                cfprFaultInstType,
                cfprFaultInstCause,
                cfprFaultInstSeverity,
                cfprFaultInstOccur,
                cfprFaultInstId
            FROM CISCO-FIREPOWER-FAULT-MIB;

ciscoFirepowerMIBNotifs MODULE-IDENTITY
        LAST-UPDATED  "201703151700Z" 
        ORGANIZATION  "Cisco"
        CONTACT-INFO
            "Cisco Systems
            Customer Service

            Postal: 170 West Tasman Drive
            San Jose, CA  95134
            USA

            Tel: +1 800 553-NETS

            E-mail: savbu-snmp-dev@cisco.com"
      DESCRIPTION
         "Fault traps (notifications) issued by the Firepower system"
      REVISION "201001290000Z" 
      DESCRIPTION
         "Initial version of this MIB module."
   ::= { ciscoFirepowerMIB 0 }

cfprFaultActiveNotif NOTIFICATION-TYPE
      OBJECTS  {
                cfprFaultInstInstanceId,
                cfprFaultInstDescr,
                cfprFaultInstAffectedObjectId,
                cfprFaultInstAffectedObjectDn,
                cfprFaultInstCreated,
                cfprFaultInstLastTransition,
                cfprFaultInstCode,
                cfprFaultInstType,
                cfprFaultInstCause,
                cfprFaultInstSeverity,
                cfprFaultInstOccur,
                cfprFaultInstId
               }
      STATUS current
      DESCRIPTION
          "This notification is generated by a Firepower node whenever a fault
          is active and the fault state changes."
      ::= { ciscoFirepowerMIBNotifs 1 }

cfprFaultClearNotif NOTIFICATION-TYPE
      OBJECTS  {
                cfprFaultInstInstanceId,
                cfprFaultInstDescr,
                cfprFaultInstAffectedObjectId,
                cfprFaultInstAffectedObjectDn,
                cfprFaultInstCreated,
                cfprFaultInstLastTransition,
                cfprFaultInstCode,
                cfprFaultInstType,
                cfprFaultInstCause,
                cfprFaultInstSeverity,
                cfprFaultInstOccur,
                cfprFaultInstId
               }
      STATUS current
      DESCRIPTION
          "This notification is generated by a Firepower node whenever a fault
          is cleared."
      ::= { ciscoFirepowerMIBNotifs 2 }

END
