-- *****************************************************************
-- CISCO-TRUSTSEC-CAPABILITY.my:
-- Cisco CISCO-TRUSTSEC-MIB AGENT-CAPABILITIES
--   
-- February 2009, Dipesh Gorashia
--   
-- Copyright (c) 2009-2012 by Cisco Systems Inc.
-- All rights reserved.
-- ****************************************************************

CISCO-TRUSTSEC-CAPABILITY DEFINITIONS ::= BEGIN

IMPORTS
    MODULE-IDENTITY,
    Unsigned32
        FROM SNMPv2-SMI
    AGENT-CAPABILITIES
        FROM SNMPv2-CONF
    SnmpAdminString
        FROM SNMP-FRAMEWORK-MIB
    RowStatus
        FROM SNMPv2-TC
    CtsPasswordEncryptionType
        FROM CISCO-TRUSTSEC-TC-MIB
    ciscoAgentCapability
        FROM CISCO-SMI;


ciscoTrustSecCapability MODULE-IDENTITY
    LAST-UPDATED    "201209070000Z"
    ORGANIZATION    "Cisco Systems, Inc."
    CONTACT-INFO
            "Cisco Systems
            Customer Service

            Postal: 170 West Tasman Drive
            San Jose, CA  95134
            USA

            Tel: +1 800 553-NETS

            E-mail: cs-san@cisco.com,
                    cs-lan-switch-snmp@cisco.com"
    DESCRIPTION
        "The capabilities description of
        CISCO-TRUSTSEC-MIB."
    REVISION        "201209070000Z"
    DESCRIPTION
        "Added capability statements
        - ciscoTrustSecCapV15R0101SYPCat6kSup2T
        - ciscoTrustSecCapV15R0101SYPCat6kSup720

        Added VARITION for object ctsSgtAssignmentMethod
        to the following capability statements:
        - ciscoTrustSecCapV12R0250SYPCat6k
        - ciscoTrustSecCapV15R0001SYPCat6k"
    REVISION        "201109280000Z"
    DESCRIPTION
        "Added capability statement
        ciscoTrustSecCapV15R0001SYPCat6k."
    REVISION        "201011020000Z"
    DESCRIPTION
        "Initial version of this MIB module."
    ::= { ciscoAgentCapability 598 }



ciscoTrustSecCapV12R0250SYPCat6k AGENT-CAPABILITIES
    PRODUCT-RELEASE "Cisco IOS 12.2(50)SY on Catalyst 6000/6500
                     series devices."
    STATUS          current
    DESCRIPTION
        "CISCO-TRUSTSEC-MIB capabilities."

    SUPPORTS        CISCO-TRUSTSEC-MIB
    INCLUDES        {
                        ciscoTrustSecCacheGroup,
                        ciscoTrustSecSgtGroup,
                        ciscoTrustSecCredentialsGroup,
                        ciscoTrustSecHwKeystoreInfoGroup,
                        ciscoTrustSecEnvDataGroup,
                        ciscoTrustSecSgtAssignmentGroup
                    }
    VARIATION       ctsCacheNvStorage
    SYNTAX          SnmpAdminString (SIZE (0..158))
    DESCRIPTION
        "Only a limited set of values is supported."

    VARIATION       ctsSecurityGroupTagId
    SYNTAX          Unsigned32 (0..65533)
    DESCRIPTION
        "Only limited set of values is supported."

    VARIATION       ctsDeviceId
    SYNTAX          SnmpAdminString (SIZE (0..80))
    DESCRIPTION
        "Only a limited set of values is supported."

    VARIATION       ctsDevicePasswordType
    SYNTAX          CtsPasswordEncryptionType {
                        none(2),
                        clearText(3)
                    }
    DESCRIPTION
        "Only a limited set of enumerated values is supported."

    VARIATION       ctsPacStatus
    SYNTAX          RowStatus {
                        active(1),
                        destroy(6)
                    }
    DESCRIPTION
        "Only a limited set of enumerated values is
        supported."

    VARIATION       ctsSgtAssignmentMethod
    DESCRIPTION
        "Objct is instatinated only on Catalyst 6000/6500
        series devices with Supervisor 2T present."

    ::= { ciscoTrustSecCapability 1 }

ciscoTrustSecCapV15R0001SYPCat6k AGENT-CAPABILITIES
    PRODUCT-RELEASE "Cisco IOS 15.0(1)SY on Catalyst 6000/6500
                     series devices."
    STATUS          current
    DESCRIPTION
        "CISCO-TRUSTSEC-MIB capabilities."

    SUPPORTS        CISCO-TRUSTSEC-MIB
    INCLUDES        {
                        ciscoTrustSecCacheGroup,
                        ciscoTrustSecSgtGroup,
                        ciscoTrustSecCredentialsGroup,
                        ciscoTrustSecHwKeystoreInfoGroup,
                        ciscoTrustSecEnvDataGroup,
                        ciscoTrustSecSgtAssignmentGroup,
                        ciscoTrustSecEnvSecGroupNameGroup
                    }
    VARIATION       ctsCacheNvStorage
    SYNTAX          SnmpAdminString (SIZE (0..158))
    DESCRIPTION
        "Only a limited set of values is supported."

    VARIATION       ctsSecurityGroupTagId
    SYNTAX          Unsigned32 (0..65533)
    DESCRIPTION
        "Only limited set of values is supported."

    VARIATION       ctsDeviceId
    SYNTAX          SnmpAdminString (SIZE (0..80))
    DESCRIPTION
        "Only a limited set of values is supported."

    VARIATION       ctsDevicePasswordType
    SYNTAX          CtsPasswordEncryptionType {
                        none(2),
                        clearText(3)
                    }
    DESCRIPTION
        "Only a limited set of enumerated values is supported."

    VARIATION       ctsPacStatus
    SYNTAX          RowStatus {
                        active(1),
                        destroy(6)
                    }
    DESCRIPTION
        "Only a limited set of enumerated values is
        supported."

    VARIATION       ctsSgtAssignmentMethod
    DESCRIPTION
        "Objct is instatinated only on Catalyst 6000/6500
        series devices with Supervisor 2T present."

    ::= { ciscoTrustSecCapability 2 }

ciscoTrustSecCapV15R0101SYPCat6kSup2T AGENT-CAPABILITIES
    PRODUCT-RELEASE "Cisco IOS 15.1(1)SY on Catalyst 6000/6500
                     series devices with Supervisor 2T present."
    STATUS          current
    DESCRIPTION
        "CISCO-TRUSTSEC-MIB capabilities."

    SUPPORTS        CISCO-TRUSTSEC-MIB
    INCLUDES        {
                        ciscoTrustSecCacheGroup,
                        ciscoTrustSecSgtGroup,
                        ciscoTrustSecCredentialsGroup,
                        ciscoTrustSecHwKeystoreInfoGroup,
                        ciscoTrustSecEnvDataGroup,
                        ciscoTrustSecSgtAssignmentGroup,
                        ciscoTrustSecEnvSecGroupNameGroup,
                        ciscoTrustSecSwKeystoreNotifsInfoGroup,
                        ciscoTrustSecSwKeystoreNotifsControlGroup,
                        ciscoTrustSecSwKeystoreNotifsGroup,
                        ciscoTrustSecFileErrNotifsInfoGroup,
                        ciscoTrustSecNotifsMessageStringInfoGroup,
                        ciscoTrustSecCacheFileNotifsControlGroup,
                        ciscoTrustSecCacheFileNotifsGroup,
                        ciscoTrustSecCtrDrbgNotifsControlGroup,
                        ciscoTrustSecCtrDrbgNotifsGroup
                    }
    VARIATION       ctsCacheNvStorage
    SYNTAX          SnmpAdminString (SIZE (0..158))
    DESCRIPTION
        "Only a limited set of values is supported."

    VARIATION       ctsSecurityGroupTagId
    SYNTAX          Unsigned32 (0..65533)
    DESCRIPTION
        "Only limited set of values is supported."

    VARIATION       ctsDeviceId
    SYNTAX          SnmpAdminString (SIZE (0..80))
    DESCRIPTION
        "Only a limited set of values is supported."

    VARIATION       ctsDevicePasswordType
    SYNTAX          CtsPasswordEncryptionType {
                        none(2),
                        clearText(3)
                    }
    DESCRIPTION
        "Only a limited set of enumerated values is supported."

    VARIATION       ctsPacStatus
    SYNTAX          RowStatus {
                        active(1),
                        destroy(6)
                    }
    DESCRIPTION
        "Only a limited set of enumerated values is
        supported."

    ::= { ciscoTrustSecCapability 3 }

ciscoTrustSecCapV15R0101SYPCat6kSup720 AGENT-CAPABILITIES
    PRODUCT-RELEASE "Cisco IOS 15.1(1)SY on Catalyst 6000/6500
                     series devices with Supervisor 720 present."
    STATUS          current
    DESCRIPTION
        "CISCO-TRUSTSEC-MIB capabilities."

    SUPPORTS        CISCO-TRUSTSEC-MIB
    INCLUDES        {
                        ciscoTrustSecCacheGroup,
                        ciscoTrustSecSgtGroup,
                        ciscoTrustSecCredentialsGroup,
                        ciscoTrustSecHwKeystoreInfoGroup,
                        ciscoTrustSecEnvDataGroup,
                        ciscoTrustSecEnvSecGroupNameGroup,
                        ciscoTrustSecSwKeystoreNotifsInfoGroup,
                        ciscoTrustSecSwKeystoreNotifsControlGroup,
                        ciscoTrustSecSwKeystoreNotifsGroup,
                        ciscoTrustSecFileErrNotifsInfoGroup,
                        ciscoTrustSecNotifsMessageStringInfoGroup,
                        ciscoTrustSecCacheFileNotifsControlGroup,
                        ciscoTrustSecCacheFileNotifsGroup,
                        ciscoTrustSecCtrDrbgNotifsControlGroup,
                        ciscoTrustSecCtrDrbgNotifsGroup
                    }
    VARIATION       ctsCacheNvStorage
    SYNTAX          SnmpAdminString (SIZE (0..158))
    DESCRIPTION
        "Only a limited set of values is supported."

    VARIATION       ctsSecurityGroupTagId
    SYNTAX          Unsigned32 (0..65533)
    DESCRIPTION
        "Only limited set of values is supported."

    VARIATION       ctsDeviceId
    SYNTAX          SnmpAdminString (SIZE (0..80))
    DESCRIPTION
        "Only a limited set of values is supported."

    VARIATION       ctsDevicePasswordType
    SYNTAX          CtsPasswordEncryptionType {
                        none(2),
                        clearText(3)
                    }
    DESCRIPTION
        "Only a limited set of enumerated values is supported."

    VARIATION       ctsPacStatus
    SYNTAX          RowStatus {
                        active(1),
                        destroy(6)
                    }
    DESCRIPTION
        "Only a limited set of enumerated values is
        supported."

    ::= { ciscoTrustSecCapability 4 }

END
