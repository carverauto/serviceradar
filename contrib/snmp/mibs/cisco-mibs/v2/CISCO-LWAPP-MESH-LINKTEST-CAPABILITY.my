-- *******************************************************************
-- CISCO-LWAPP-MESH-LINKTEST MIB CAPABILITY
--
-- November 18, 2020
--
-- Copyright (c) 2020, 2022 by Cisco Systems, Inc.
-- All rights reserved.
-- *******************************************************************

CISCO-LWAPP-MESH-LINKTEST-CAPABILITY DEFINITIONS ::= BEGIN


IMPORTS
       MODULE-IDENTITY
           FROM SNMPv2-SMI
       AGENT-CAPABILITIES
           FROM SNMPv2-CONF
       ciscoAgentCapability
           FROM CISCO-SMI;


ciscoLwappMeshLinktestCapability  MODULE-IDENTITY

       LAST-UPDATED         "202011180000Z"
       ORGANIZATION         "Cisco Systems, Inc."
       CONTACT-INFO
               "Cisco Systems
               Customer Service

               Postal: 170 W Tasman Drive
               San Jose, CA  95134
               USA

               Tel: +1 800 553-NETS

               E-mail: cs-wnbu-snmp@cisco.com"

       DESCRIPTION
               "Agent capabilities for
               CISCO-LWAPP-MESH-LINKTEST-MIB "
       REVISION      "202011180000Z"
       DESCRIPTION
               "Initial version of this MIB module. "

   ::= { ciscoAgentCapability 1170 }

ciscoLwappMeshLinktestCapabilityCEV1R0 AGENT-CAPABILITIES

       PRODUCT-RELEASE "Cisco EWLC 1.0"
       STATUS          current
       DESCRIPTION     "CISCO-LWAPP-MESH-LINKTEST--MIB capabilities."

       SUPPORTS        CISCO-LWAPP-MESH-LINKTEST-MIB
       INCLUDES        {
                        ciscoLwappMeshLinkTestConfig
                       }

       VARIATION       clMeshLtPurgeTime
       ACCESS          not-implemented
       DESCRIPTION     "Not supported"

   ::= { ciscoLwappMeshLinktestCapability 1 }

END


--%DNP%  MLC -Compiled MLC

--%DNP%  MTF -TRUE MTF
