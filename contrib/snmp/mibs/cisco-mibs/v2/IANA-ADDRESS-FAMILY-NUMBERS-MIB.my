-- *****************************************************************
-- IANA-ADDRESS-FAMILY-NUMBERS-MIB
--
-- Apr 2001, Arvind Prabhudev
--
-- Copyright (c) 2001 by cisco Systems, Inc.
-- All rights reserved.
-- *****************************************************************

------------------------------------------------------------------------
-- DISCLAIMER
-- ***********
-- This is a copy of the IANA-ADDRESS-FAMILY-NUMBERS-MIB, 
-- put out by IANA.
--
-- In case of differences between this file and the file available at
-- ftp://ftp.isi.edu/mib/ianaaddressfamilynumbers.mib, 
-- then the version at that URL should be used instead of this file.
------------------------------------------------------------------------

IANA-ADDRESS-FAMILY-NUMBERS-MIB DEFINITIONS ::= BEGIN

IMPORTS
    MODULE-IDENTITY,
    mib-2                               FROM SNMPv2-SMI
    TEXTUAL-CONVENTION                  FROM SNMPv2-TC;

ianaAddressFamilyNumbers MODULE-IDENTITY
    LAST-UPDATED "200009080000Z"  -- September 8, 2000
    ORGANIZATION "IANA"
    CONTACT-INFO
        "Postal:    Internet Assigned Numbers Authority
                    Internet Corporation for Assigned Names
                    and Numbers
                    4676 Admiralty Way, Suite 330
                    Marina del Rey, CA 90292-6601
                    USA

        Tel:    +1  310-823-9358
        E-Mail: iana@iana.org"
    DESCRIPTION
        "The MIB module defines the AddressFamilyNumbers
        textual convention."

    -- revision history

    REVISION     "200009080000Z"  -- September 8, 2000
    DESCRIPTION  "AddressFamilyNumbers assignments 19 to
                 xtpoveripv4, 20 to xtpoveripv6, and 21 to
                 xtpnativemodextp." 

    REVISION     "200003010000Z"  -- March 1, 2000
    DESCRIPTION  "AddressFamilyNumbers assignment 17 to distinguishedname. 
                 AddressFamilyNumbers assignment 18 to asnumber."

    REVISION     "200002040000Z"  -- February 4, 2000
    DESCRIPTION  "AddressFamilyNumbers assignment 16 to dns."

    REVISION     "9908260000Z"  -- August 26, 1999
    DESCRIPTION  "Initial version, for more explanation, see RFC 2677."

    ::= { mib-2 72 }


AddressFamilyNumbers ::= TEXTUAL-CONVENTION

    STATUS       current
    DESCRIPTION
        "The definition of this textual convention with the
        addition of newly assigned values is published
        periodically by the IANA, in either the Assigned
        Numbers RFC, or some derivative of it specific to
        Internet Network Management number assignments.
        (The latest arrangements can be obtained by
        contacting the IANA.)

        The enumerations are described as:

        other(0),    -- none of the following
        ipV4(1),     -- IP Version 4
        ipV6(2),     -- IP Version 6
        nsap(3),     -- NSAP
        hdlc(4),     -- (8-bit multidrop)
        bbn1822(5),
        all802(6),   -- (includes all 802 media
                     --   plus Ethernet 'canonical format')
        e163(7),
        e164(8),     -- (SMDS, Frame Relay, ATM)
        f69(9),      -- (Telex)
        x121(10),    -- (X.25, Frame Relay)
        ipx(11),     -- IPX (Internet Protocol Exchange)
        appletalk(12),  -- Apple Talk
        decnetIV(13),   -- DEC Net Phase IV
        banyanVines(14),  -- Banyan Vines
        e164withNsap(15),
                     -- (E.164 with NSAP format subaddress)
        dns(16),     -- (Domain Name System)
        distinguishedname(17), -- (Distinguished Name, per X.500)
        asnumber(18), -- (16-bit quantity, per the AS number space)
        reserved(65535)


        Requests for new values should be made to IANA via
        email (iana@iana.org)."

    SYNTAX  INTEGER {
                other(0),
                ipV4(1),
                ipV6(2),
                nsap(3),
                hdlc(4),
                bbn1822(5),
                all802(6),
                e163(7),
                e164(8),
                f69(9),
                x121(10),
                ipx(11),
                appletalk(12),
                decnetIV(13),
                banyanVines(14),
                e164withNsap(15),
                dns(16),
                distinguishedname(17), -- (Distinguished Name, per X.500)
                asnumber(18), -- (16-bit quantity, per the AS numberspace)
                xtpoveripv4(19), -- XTP over version 4
                xtpoveripv6(20), -- XTP over version 6
                xtpnativemodextp(21), -- XTP native mode XTP 
                reserved(65535)
            }
    END
