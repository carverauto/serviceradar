-- *******************************************************************
-- CISCO-LWAPP-RF MIB CAPABILITY
--
-- November 18, 2020
--
-- Copyright (c) 2020, 2022 by Cisco Systems, Inc.
-- All rights reserved.
-- *******************************************************************

CISCO-LWAPP-RF-CAPABILITY DEFINITIONS ::= BEGIN


IMPORTS
       MODULE-IDENTITY
           FROM SNMPv2-SMI
       AGENT-CAPABILITIES
           FROM SNMPv2-CONF
       ciscoAgentCapability
           FROM CISCO-SMI;


ciscoLwappRfCapability  MODULE-IDENTITY

       LAST-UPDATED         "202011180000Z"
       ORGANIZATION         "Cisco Systems, Inc."
       CONTACT-INFO
               "Cisco Systems
               Customer Service

               Postal: 170 W Tasman Drive
               San Jose, CA  95134
               USA

               Tel: +1 800 553-NETS

               E-mail: cs-wnbu-snmp@cisco.com"

       DESCRIPTION
               "Agent capabilities for
               CISCO-LWAPP-RF-MIB "
       REVISION      "202011180000Z"
       DESCRIPTION
               "Initial version of this MIB module. "

   ::= { ciscoAgentCapability 1155 }

ciscoLwappRfCapabilityCEV1R0 AGENT-CAPABILITIES

       PRODUCT-RELEASE "Cisco EWLC 1.0"
       STATUS          current
       DESCRIPTION     "CISCO-LWAPP-RF--MIB capabilities."

       SUPPORTS        CISCO-LWAPP-RF-MIB
       INCLUDES        {
                           cLRFProfileTable,
                           cLRFProfileChannelListTable,
                           cLRFProfileRemoveChannelTable,
                           cLAPGroupsRFProfileTable
                       }

       VARIATION       cLRFProfile11nOnly
       ACCESS          not-implemented
       DESCRIPTION     "Not supported"

       VARIATION       cLRFProfileOutOfBoxAPConfig
       ACCESS          not-implemented
       DESCRIPTION     "Not supported"

       VARIATION       cLRFProfileOutOfBoxAPPersistenceConfig
       ACCESS          not-implemented
       DESCRIPTION     "Not supported"

       VARIATION       cLRFProfileChannelListEntry
       ACCESS          not-implemented
       DESCRIPTION     "Not supported"

       VARIATION       cLRFProfileChanNumber
       ACCESS          not-implemented
       DESCRIPTION     "Not supported"

       VARIATION       cLRFProfileChanAddRemove
       ACCESS          not-implemented
       DESCRIPTION     "Not supported"

       VARIATION       cLRFProfileChanRowStatus
       ACCESS          not-implemented
       DESCRIPTION     "Not supported"

       VARIATION       cLRFProfileRemovedChannelDcaState
       ACCESS          not-implemented
       DESCRIPTION     "Not supported"

       VARIATION       cLAPGroupsRFProfileEntry
       ACCESS          not-implemented
       DESCRIPTION     "Not supported"

       VARIATION       cLAPGroups802dot11bgRFProfileName
       ACCESS          not-implemented
       DESCRIPTION     "Not supported"

       VARIATION       cLAPGroups802dot11aRFProfileName
       ACCESS          not-implemented
       DESCRIPTION     "Not supported"

   ::= { ciscoLwappRfCapability 1 }

END
