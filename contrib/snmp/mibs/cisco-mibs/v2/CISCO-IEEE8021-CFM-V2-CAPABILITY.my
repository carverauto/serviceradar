-- *****************************************************************
-- CISCO-IEEE8021-CFM-V2-CAPABILITY.my:
-- Cisco IEEE8021-CFM-V2-MIB AGENT-CAPABILITIES
--   
-- February 2009, Wen Xu
--   
-- Copyright (c) 2008-2009, 2010 by Cisco Systems Inc.
-- All rights reserved.
-- ****************************************************************

CISCO-IEEE8021-CFM-V2-CAPABILITY DEFINITIONS ::= BEGIN

IMPORTS
    MODULE-IDENTITY,
    Unsigned32
        FROM SNMPv2-SMI
    AGENT-CAPABILITIES
        FROM SNMPv2-CONF
    ciscoAgentCapability
        FROM CISCO-SMI;


ciscoIeee8021CfmV2Capability MODULE-IDENTITY
    LAST-UPDATED    "201002150000Z"
    ORGANIZATION    "Cisco Systems, Inc."
    CONTACT-INFO
            "Cisco Systems
            Customer Service

            Postal: 170 West Tasman Drive
            San Jose, CA 95134
            USA

            Tel: +1 800 553-NETS

            E-mail: cs-lan-switch-snmp@cisco.com"
    DESCRIPTION
        "The capabilities description of IEEE8021-CFM-V2-MIB."
    REVISION        "201002150000Z"
    DESCRIPTION
        "Added capability statement
        ciscoIeee8021CfmV2CapV12R0254SE."
    REVISION        "200902060000Z"
    DESCRIPTION
        "Initial version of this MIB module."
    ::= { ciscoAgentCapability 579 }



ciscoIeee8021CfmV2CapCatOSV08R0702 AGENT-CAPABILITIES
    PRODUCT-RELEASE "Cisco CatOS 8.7(2)."
    STATUS          current
    DESCRIPTION
        "IEEE8021-CFM-V2-MIB capabilities."

    SUPPORTS        IEEE8021-CFM-V2-MIB
    INCLUDES        {
                        ieee8021CfmStackGroup,
                        ieee8021CfmMaGroup,
                        ieee8021CfmConfigErrorListGroup
                    }
    VARIATION       ieee8021CfmMaCompPrimarySelectorType
    ACCESS          read-only
    DESCRIPTION
        "Write access is not supported."

    VARIATION       ieee8021CfmMaCompPrimarySelectorOrNone
    SYNTAX          Unsigned32 (1..4094)
    DESCRIPTION
        "Only limited set of values is supported."

    VARIATION       ieee8021CfmMaCompNumberOfVids
    ACCESS          read-only
    DESCRIPTION
        "Write access is not supported."

    VARIATION       ieee8021CfmMaCompRowStatus
    SYNTAX          INTEGER  {
                        active(1),
                        createAndGo(4),
                        destroy(6)
                    }
    DESCRIPTION
        "Only limited set of enumerated values
        is supported."

    VARIATION       ieee8021CfmMaCompMhfCreation
    ACCESS          not-implemented
    DESCRIPTION
        "This object is not supported."

    VARIATION       ieee8021CfmMaCompIdPermission
    ACCESS          not-implemented
    DESCRIPTION
        "This object is not supported."

    ::= { ciscoIeee8021CfmV2Capability 1 }

ciscoIeee8021CfmV2CapV12R0254SE AGENT-CAPABILITIES
    PRODUCT-RELEASE "Cisco IOS 12.2(54)SE."
    STATUS          current
    DESCRIPTION
        "IEEE8021-CFM-V2-MIB capabilities"

    SUPPORTS        IEEE8021-CFM-V2-MIB
    INCLUDES        {
                        ieee8021CfmStackGroup,
                        ieee8021CfmMaGroup,
                        ieee8021CfmVlanIdGroup,
                        ieee8021CfmDefaultMdGroup,
                        ieee8021CfmConfigErrorListGroup
                    }
    VARIATION       ieee8021CfmVlanPrimarySelector
    ACCESS          read-only
    DESCRIPTION
        "create/write is not implemented"

    VARIATION       ieee8021CfmVlanRowStatus
    ACCESS          read-only
    DESCRIPTION
        "create/write is not implemented"

    VARIATION       ieee8021CfmMaCompPrimarySelectorType
    ACCESS          read-only
    DESCRIPTION
        "create/write is not implemented"

    VARIATION       ieee8021CfmMaCompPrimarySelectorOrNone
    ACCESS          read-only
    DESCRIPTION
        "create/write is not implemented"

    VARIATION       ieee8021CfmMaCompMhfCreation
    ACCESS          read-only
    DESCRIPTION
        "create/write is not implemented"

    VARIATION       ieee8021CfmMaCompIdPermission
    ACCESS          read-only
    DESCRIPTION
        "create/write is not implemented"

    VARIATION       ieee8021CfmMaCompNumberOfVids
    ACCESS          read-only
    DESCRIPTION
        "create/write is not implemented"

    VARIATION       ieee8021CfmMaCompRowStatus
    ACCESS          read-only
    DESCRIPTION
        "create/write is not implemented"

    VARIATION       ieee8021CfmVlanPrimarySelector
    ACCESS          read-only
    DESCRIPTION
        "create/write is not implemented"

    VARIATION       ieee8021CfmVlanRowStatus
    ACCESS          read-only
    DESCRIPTION
        "create/write is not implemented"

    VARIATION       ieee8021CfmDefaultMdLevel
    ACCESS          read-only
    DESCRIPTION
        "Write access is not supported"

    VARIATION       ieee8021CfmDefaultMdMhfCreation
    ACCESS          read-only
    DESCRIPTION
        "Write access is not supported"

    VARIATION       ieee8021CfmDefaultMdIdPermission
    ACCESS          read-only
    DESCRIPTION
        "Write access is not supported"

    ::= { ciscoIeee8021CfmV2Capability 2 }

END
