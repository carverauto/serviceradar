-- *******************************************************************
-- CISCO-LWAPP-WLAN MIB CAPABILITY
--
-- November 18, 2020
--
-- Copyright (c) 2020, 2022 by Cisco Systems, Inc.
-- All rights reserved.
-- *******************************************************************

CISCO-LWAPP-WLAN-CAPABILITY DEFINITIONS ::= BEGIN


IMPORTS
       MODULE-IDENTITY
           FROM SNMPv2-SMI
       AGENT-CAPABILITIES
           FROM SNMPv2-CONF
       ciscoAgentCapability
           FROM CISCO-SMI;


ciscoLwappWlanCapability  MODULE-IDENTITY

       LAST-UPDATED         "202011180000Z"
       ORGANIZATION         "Cisco Systems, Inc."
       CONTACT-INFO
               "Cisco Systems
               Customer Service

               Postal: 170 W Tasman Drive
               San Jose, CA  95134
               USA

               Tel: +1 800 553-NETS

               E-mail: cs-wnbu-snmp@cisco.com"

       DESCRIPTION
               "Agent capabilities for
               CISCO-LWAPP-WLAN-MIB "
       REVISION      "202011180000Z"
       DESCRIPTION
               "Initial version of this MIB module. "

   ::= { ciscoAgentCapability 1154 }

ciscoLwappWlanCapabilityCEV1R0 AGENT-CAPABILITIES

       PRODUCT-RELEASE "Cisco EWLC 1.0"
       STATUS          current
       DESCRIPTION     "CISCO-LWAPP-WLAN--MIB capabilities."

       SUPPORTS        CISCO-LWAPP-WLAN-MIB
       INCLUDES        {
                           cLWlanConfigQosTable,
                           cLWlanHotSpot2OperatorTable,
                           cLWlanServiceAdvertisementTable,
                           cLAPGroupsVenueConfigTable,
                           cLWlan11uTable,
                           cLWlan11uDomainTable,
                           cLAPGroupsPortConfigTable,
                           cLAPGroupNasIdConfigTable,
                           cLAPGroupConfigTable,
                           cLWlanHotSpot2PortConfigTable,
                           cLWlan11uOuiTable,
                           cLWlanConfigIosTable,
                           cLWlanConfigTable,
                           cLWlanHotSpot2ConfigTable,
                           cLWlan11uRealmEapTable,
                           cLAPGroupsExtModuleConfigTable,
                           cLWlanFlexibleNetflowTable,
                           cLAPGroupQinqConfigTable,
                           cLPolicyConfigTable,
                           cLWlanConfigClientTable,
                           cLWlan11u3gppTable,
                           cLAPGroupsPolicyTable,
                           cLPolicyActiveHoursTable,
                           cLAPGroupsMultipleVenueTable,
                           cLWlan11uRealmTable,
                           cLAPGroupsVlanConfigTable,
                           cLWlan11uRealmEapAuthTable,
                           cLPolicyDeviceTable,
                           cLAPGroupsHyperlocationConfigTable
                       }

       VARIATION       cLWlanConfigQosEntry
       ACCESS          not-implemented
       DESCRIPTION     "Not supported"

       VARIATION       cLWlanClientDSAverageDataRate
       ACCESS          not-implemented
       DESCRIPTION     "Not supported"

       VARIATION       cLWlanClientUSAverageDataRate
       ACCESS          not-implemented
       DESCRIPTION     "Not supported"

       VARIATION       cLWlanClientDSBurstDataRate
       ACCESS          not-implemented
       DESCRIPTION     "Not supported"

       VARIATION       cLWlanClientUSBurstDataRate
       ACCESS          not-implemented
       DESCRIPTION     "Not supported"

       VARIATION       cLWlanClientDSAvgRealTimeDataRate
       ACCESS          not-implemented
       DESCRIPTION     "Not supported"

       VARIATION       cLWlanClientUSAvgRealTimeDataRate
       ACCESS          not-implemented
       DESCRIPTION     "Not supported"

       VARIATION       cLWlanClientDSBurstRealTimeDataRate
       ACCESS          not-implemented
       DESCRIPTION     "Not supported"

       VARIATION       cLWlanClientUSBurstRealTimeDataRate
       ACCESS          not-implemented
       DESCRIPTION     "Not supported"

       VARIATION       cLWlanSsidDSAverageDataRate
       ACCESS          not-implemented
       DESCRIPTION     "Not supported"

       VARIATION       cLWlanSsidUSAverageDataRate
       ACCESS          not-implemented
       DESCRIPTION     "Not supported"

       VARIATION       cLWlanSsidDSBurstDataRate
       ACCESS          not-implemented
       DESCRIPTION     "Not supported"

       VARIATION       cLWlanSsidUSBurstDataRate
       ACCESS          not-implemented
       DESCRIPTION     "Not supported"

       VARIATION       cLWlanSsidDSAvgRealTimeDataRate
       ACCESS          not-implemented
       DESCRIPTION     "Not supported"

       VARIATION       cLWlanSsidUSAvgRealTimeDataRate
       ACCESS          not-implemented
       DESCRIPTION     "Not supported"

       VARIATION       cLWlanSsidDSBurstRealTimeDataRate
       ACCESS          not-implemented
       DESCRIPTION     "Not supported"

       VARIATION       cLWlanSsidUSBurstRealTimeDataRate
       ACCESS          not-implemented
       DESCRIPTION     "Not supported"

       VARIATION       cLWlanWlanDSAverageDataRate
       ACCESS          not-implemented
       DESCRIPTION     "Not supported"

       VARIATION       cLWlanWlanUSAverageDataRate
       ACCESS          not-implemented
       DESCRIPTION     "Not supported"

       VARIATION       cLWlanWlanDSBurstDataRate
       ACCESS          not-implemented
       DESCRIPTION     "Not supported"

       VARIATION       cLWlanWlanUSBurstDataRate
       ACCESS          not-implemented
       DESCRIPTION     "Not supported"

       VARIATION       cLWlanWlanDSAvgRealTimeDataRate
       ACCESS          not-implemented
       DESCRIPTION     "Not supported"

       VARIATION       cLWlanWlanUSAvgRealTimeDataRate
       ACCESS          not-implemented
       DESCRIPTION     "Not supported"

       VARIATION       cLWlanWlanDSBurstRealTimeDataRate
       ACCESS          not-implemented
       DESCRIPTION     "Not supported"

       VARIATION       cLWlanWlanUSBurstRealTimeDataRate
       ACCESS          not-implemented
       DESCRIPTION     "Not supported"

       VARIATION       cLWlanHotSpot2OperatorEntry
       ACCESS          not-implemented
       DESCRIPTION     "Not supported"

       VARIATION       cLWlanHotSpot2OperatorIndex
       ACCESS          not-implemented
       DESCRIPTION     "Not supported"

       VARIATION       cLWlanHotSpot2OperatorName
       ACCESS          not-implemented
       DESCRIPTION     "Not supported"

       VARIATION       cLWlanHotSpot2OperatorLanguage
       ACCESS          not-implemented
       DESCRIPTION     "Not supported"

       VARIATION       cLWlanHotSpot2OperatorRowStatus
       ACCESS          not-implemented
       DESCRIPTION     "Not supported"

       VARIATION       cLWlanServiceAdvertisementEntry
       ACCESS          not-implemented
       DESCRIPTION     "Not supported"

       VARIATION       cLWlanServiceAdvertisementStatus
       ACCESS          not-implemented
       DESCRIPTION     "Not supported"

       VARIATION       cLWlanServiceAdvertisementMsapServerIndex
       ACCESS          not-implemented
       DESCRIPTION     "Not supported"

       VARIATION       cLAPGroupsVenueConfigEntry
       ACCESS          not-implemented
       DESCRIPTION     "Not supported"

       VARIATION       cLAPGroupsVenueConfigVenueGroup
       ACCESS          not-implemented
       DESCRIPTION     "Not supported"

       VARIATION       cLAPGroupsVenueConfigVenueType
       ACCESS          not-implemented
       DESCRIPTION     "Not supported"

       VARIATION       cLAPGroupsVenueConfigVenueName
       ACCESS          not-implemented
       DESCRIPTION     "Not supported"

       VARIATION       cLAPGroupsVenueConfigLanguage
       ACCESS          not-implemented
       DESCRIPTION     "Not supported"

       VARIATION       cLAPGroupsOperatingClass
       ACCESS          not-implemented
       DESCRIPTION     "Not supported"

       VARIATION       cLWlan11uEntry
       ACCESS          not-implemented
       DESCRIPTION     "Not supported"

       VARIATION       cLWlan11uStatus
       ACCESS          not-implemented
       DESCRIPTION     "Not supported"

       VARIATION       cLWlan11uInternetAccess
       ACCESS          not-implemented
       DESCRIPTION     "Not supported"

       VARIATION       cLWlan11uNetworkType
       ACCESS          not-implemented
       DESCRIPTION     "Not supported"

       VARIATION       cLWlan11uVenueGroup
       ACCESS          not-implemented
       DESCRIPTION     "Not supported"

       VARIATION       cLWlan11uVenueType
       ACCESS          not-implemented
       DESCRIPTION     "Not supported"

       VARIATION       cLWlan11uVenueName
       ACCESS          not-implemented
       DESCRIPTION     "Not supported"

       VARIATION       cLWlan11uHessid
       ACCESS          not-implemented
       DESCRIPTION     "Not supported"

       VARIATION       cLWlan11uNetworkAuthType
       ACCESS          not-implemented
       DESCRIPTION     "Not supported"

       VARIATION       cLWlan11uIpAddressAvailIpv4
       ACCESS          not-implemented
       DESCRIPTION     "Not supported"

       VARIATION       cLWlan11uIpAddressAvailIpv6
       ACCESS          not-implemented
       DESCRIPTION     "Not supported"

       VARIATION       cLWlan11uDomainEntry
       ACCESS          not-implemented
       DESCRIPTION     "Not supported"

       VARIATION       cLWlan11uDomainIndex
       ACCESS          not-implemented
       DESCRIPTION     "Not supported"

       VARIATION       cLWlan11uDomainName
       ACCESS          not-implemented
       DESCRIPTION     "Not supported"

       VARIATION       cLWlan11uDomainRowStatus
       ACCESS          not-implemented
       DESCRIPTION     "Not supported"

       VARIATION       cLAPGroupsPortConfigEntry
       ACCESS          not-implemented
       DESCRIPTION     "Not supported"

       VARIATION       cLAPGroupsLANPortNumber
       ACCESS          not-implemented
       DESCRIPTION     "Not supported"

       VARIATION       cLAPGroupsLANPortStatus
       ACCESS          not-implemented
       DESCRIPTION     "Not supported"

       VARIATION       cLAPGroupsLANPortPoeStatus
       ACCESS          not-implemented
       DESCRIPTION     "Not supported"

       VARIATION       cLAPGroupsLANPortRlanName
       ACCESS          not-implemented
       DESCRIPTION     "Not supported"

       VARIATION       cLAPGroupsLANPortRowStatus
       ACCESS          not-implemented
       DESCRIPTION     "Not supported"

       VARIATION       cLAPGroupNasIdConfigEntry
       ACCESS          not-implemented
       DESCRIPTION     "Not supported"

       VARIATION       cLAPGroupNasId
       ACCESS          not-implemented
       DESCRIPTION     "Not supported"

       VARIATION       cLAPGroupConfigEntry
       ACCESS          not-implemented
       DESCRIPTION     "Not supported"

       VARIATION       cLApGroupPreferMode
       ACCESS          not-implemented
       DESCRIPTION     "Not supported"

       VARIATION       cLApGroupGlobalWebAuthConfig
       ACCESS          not-implemented
       DESCRIPTION     "Not supported"

       VARIATION       cLApGroupExternalWebAuthUrl
       ACCESS          not-implemented
       DESCRIPTION     "Not supported"

       VARIATION       cLWlanHotSpot2PortConfigEntry
       ACCESS          not-implemented
       DESCRIPTION     "Not supported"

       VARIATION       cLWlanHotSpot2PortConfigIndex
       ACCESS          not-implemented
       DESCRIPTION     "Not supported"

       VARIATION       cLWlanHotSpot2PortConfigIpProtocol
       ACCESS          not-implemented
       DESCRIPTION     "Not supported"

       VARIATION       cLWlanHotSpot2PortConfigPortNumber
       ACCESS          not-implemented
       DESCRIPTION     "Not supported"

       VARIATION       cLWlanHotSpot2PortConfigStatus
       ACCESS          not-implemented
       DESCRIPTION     "Not supported"

       VARIATION       cLWlanHotSpot2PortConfigRowStatus
       ACCESS          not-implemented
       DESCRIPTION     "Not supported"

       VARIATION       cLWlan11uOuiEntry
       ACCESS          not-implemented
       DESCRIPTION     "Not supported"

       VARIATION       cLWlan11uOuiIndex
       ACCESS          not-implemented
       DESCRIPTION     "Not supported"

       VARIATION       cLWlan11uOui
       ACCESS          not-implemented
       DESCRIPTION     "Not supported"

       VARIATION       cLWlan11uOuiIsBeacon
       ACCESS          not-implemented
       DESCRIPTION     "Not supported"

       VARIATION       cLWlan11uOuiRowStatus
       ACCESS          not-implemented
       DESCRIPTION     "Not supported"

       VARIATION       cLWlan11uOuiStorageType
       ACCESS          not-implemented
       DESCRIPTION     "Not supported"

       VARIATION       cLWlanIosAccountingMethodListName
       ACCESS          not-implemented
       DESCRIPTION     "Not supported"

       VARIATION       cLWlanIngressDHCPOption82Format
       ACCESS          not-implemented
       DESCRIPTION     "Not supported"

       VARIATION       cLWlanIngressDHCPOption82Ascii
       ACCESS          not-implemented
       DESCRIPTION     "Not supported"

       VARIATION       cLWlanIngressDHCPOption82Rid
       ACCESS          not-implemented
       DESCRIPTION     "Not supported"

       VARIATION       cLWlanIngressDHCPOption82Enable
       ACCESS          not-implemented
       DESCRIPTION     "Not supported"

       VARIATION       cLWlanIosScanDeferPriority
       ACCESS          not-implemented
       DESCRIPTION     "Not supported"

       VARIATION       cLWlanIosQosClientUpStreamProfileName
       ACCESS          not-implemented
       DESCRIPTION     "Not supported"

       VARIATION       cLWlanIosQosClientDownStreamProfileName
       ACCESS          not-implemented
       DESCRIPTION     "Not supported"

       VARIATION       cLWlanIngressInterface
       ACCESS          not-implemented
       DESCRIPTION     "Not supported"

       VARIATION       cLWlanNACSupport
       ACCESS          not-implemented
       DESCRIPTION     "Not supported"

       VARIATION       cLWlanWepKeyChange
       ACCESS          not-implemented
       DESCRIPTION     "Not supported"

       VARIATION       cLWlanPassiveClientEnable
       ACCESS          not-implemented
       DESCRIPTION     "Not supported"

       VARIATION       cLWlanKtsCacSupportEnabled
       ACCESS          not-implemented
       DESCRIPTION     "Not supported"

       VARIATION       cLWlanHotSpot2Enabled
       ACCESS          not-implemented
       DESCRIPTION     "Not supported"

       VARIATION       cLWlanDhcpDeviceProfiling
       ACCESS          not-implemented
       DESCRIPTION     "Not supported"

       VARIATION       cLWlanMacAuthOverDot1xEnabled
       ACCESS          not-implemented
       DESCRIPTION     "Not supported"

       VARIATION       cLWlanUserTimeout
       ACCESS          not-implemented
       DESCRIPTION     "Not supported"

       VARIATION       cLWlanUserIdleThreshold
       ACCESS          not-implemented
       DESCRIPTION     "Not supported"

       VARIATION       cLWlanHttpDeviceProfiling
       ACCESS          not-implemented
       DESCRIPTION     "Not supported"

       VARIATION       cLWlanHotSpotClearConfig
       ACCESS          not-implemented
       DESCRIPTION     "Not supported"

       VARIATION       cLWlanRadiusAuthFourthServer
       ACCESS          not-implemented
       DESCRIPTION     "Not supported"

       VARIATION       cLWlanRadiusAuthFifthServer
       ACCESS          not-implemented
       DESCRIPTION     "Not supported"

       VARIATION       cLWlanRadiusAuthSixthServer
       ACCESS          not-implemented
       DESCRIPTION     "Not supported"

       VARIATION       cLWlanRadiusAcctFourthServer
       ACCESS          not-implemented
       DESCRIPTION     "Not supported"

       VARIATION       cLWlanRadiusAcctFifthServer
       ACCESS          not-implemented
       DESCRIPTION     "Not supported"

       VARIATION       cLWlanRadiusAcctSixthServer
       ACCESS          not-implemented
       DESCRIPTION     "Not supported"

       VARIATION       cLWlanSelfAnchorEnabled
       ACCESS          not-implemented
       DESCRIPTION     "Not supported"

       VARIATION       cLWlanHotSpot2ConfigEntry
       ACCESS          not-implemented
       DESCRIPTION     "Not supported"

       VARIATION       cLWlanHotSpot2WanLinkStatus
       ACCESS          not-implemented
       DESCRIPTION     "Not supported"

       VARIATION       cLWlanHotSpot2WanSymLinkStatus
       ACCESS          not-implemented
       DESCRIPTION     "Not supported"

       VARIATION       cLWlanHotSpot2WanDownLinkSpeed
       ACCESS          not-implemented
       DESCRIPTION     "Not supported"

       VARIATION       cLWlanHotSpot2WanUpLinkSpeed
       ACCESS          not-implemented
       DESCRIPTION     "Not supported"

       VARIATION       cLWlan11uRealmEapEntry
       ACCESS          not-implemented
       DESCRIPTION     "Not supported"

       VARIATION       cLWlan11uRealmEapIndex
       ACCESS          not-implemented
       DESCRIPTION     "Not supported"

       VARIATION       cLWlan11uRealmEapMethod
       ACCESS          not-implemented
       DESCRIPTION     "Not supported"

       VARIATION       cLWlan11uRealmEapRowStatus
       ACCESS          not-implemented
       DESCRIPTION     "Not supported"

       VARIATION       cLAPGroupsExtModuleConfigEntry
       ACCESS          not-implemented
       DESCRIPTION     "Not supported"

       VARIATION       cLAPGroupsExtModuleStatus
       ACCESS          not-implemented
       DESCRIPTION     "Not supported"

       VARIATION       cLAPGroupsExtModuleRlanName
       ACCESS          not-implemented
       DESCRIPTION     "Not supported"

       VARIATION       cLWlanFlexibleNetflowEntry
       ACCESS          not-implemented
       DESCRIPTION     "Not supported"

       VARIATION       cLWlanFlexibleNetflowPolicyTypeIndex
       ACCESS          not-implemented
       DESCRIPTION     "Not supported"

       VARIATION       cLWlanFlexibleNetflowMonitorName
       ACCESS          not-implemented
       DESCRIPTION     "Not supported"

       VARIATION       cLWlanFlexibleNetflowRowStatus
       ACCESS          not-implemented
       DESCRIPTION     "Not supported"

       VARIATION       cLAPGroupQinqConfigEntry
       ACCESS          not-implemented
       DESCRIPTION     "Not supported"

       VARIATION       cLAPGroupTrafficQinqEnabled
       ACCESS          not-implemented
       DESCRIPTION     "Not supported"

       VARIATION       cLAPGroupDhcpQinqEnabled
       ACCESS          not-implemented
       DESCRIPTION     "Not supported"

       VARIATION       cLAPGroupQinqServiceVlanId
       ACCESS          not-implemented
       DESCRIPTION     "Not supported"

       VARIATION       cLPolicyConfigEntry
       ACCESS          not-implemented
       DESCRIPTION     "Not supported"

       VARIATION       cLPolicyIndex
       ACCESS          not-implemented
       DESCRIPTION     "Not supported"

       VARIATION       cLPolicyName
       ACCESS          not-implemented
       DESCRIPTION     "Not supported"

       VARIATION       cLPolicyRoleName
       ACCESS          not-implemented
       DESCRIPTION     "Not supported"

       VARIATION       cLPolicyEapType
       ACCESS          not-implemented
       DESCRIPTION     "Not supported"

       VARIATION       cLPolicyAclName
       ACCESS          not-implemented
       DESCRIPTION     "Not supported"

       VARIATION       cLPolicyVlanId
       ACCESS          not-implemented
       DESCRIPTION     "Not supported"

       VARIATION       cLPolicyQosProfile
       ACCESS          not-implemented
       DESCRIPTION     "Not supported"

       VARIATION       cLPolicySessionTimeout
       ACCESS          not-implemented
       DESCRIPTION     "Not supported"

       VARIATION       cLPolicySleepTimeout
       ACCESS          not-implemented
       DESCRIPTION     "Not supported"

       VARIATION       cLPolicyRowStatus
       ACCESS          not-implemented
       DESCRIPTION     "Not supported"

       VARIATION       cLPolicyFlexAclName
       ACCESS          not-implemented
       DESCRIPTION     "Not supported"

       VARIATION       cLPolicyAvcProfileName
       ACCESS          not-implemented
       DESCRIPTION     "Not supported"

       VARIATION       cLPolicyMdnsProfileName
       ACCESS          not-implemented
       DESCRIPTION     "Not supported"

       VARIATION       cLPolicyFlexVlanId
       ACCESS          not-implemented
       DESCRIPTION     "Not supported"

       VARIATION       cLPolicyUrlAclName
       ACCESS          not-implemented
       DESCRIPTION     "Not supported"

       VARIATION       cLPolicyOpendnsProfileName
       ACCESS          not-implemented
       DESCRIPTION     "Not supported"

       VARIATION       cLWlanClientAclName
       ACCESS          not-implemented
       DESCRIPTION     "Not supported"

       VARIATION       cLWlanClientIPv6AclName
       ACCESS          not-implemented
       DESCRIPTION     "Not supported"

       VARIATION       cLWlan11u3gppEntry
       ACCESS          not-implemented
       DESCRIPTION     "Not supported"

       VARIATION       cLWlan11u3gppIndex
       ACCESS          not-implemented
       DESCRIPTION     "Not supported"

       VARIATION       cLWlan11u3gppCountryCode
       ACCESS          not-implemented
       DESCRIPTION     "Not supported"

       VARIATION       cLWlan11u3gppNetworkCode
       ACCESS          not-implemented
       DESCRIPTION     "Not supported"

       VARIATION       cLWlan11u3gppRowStatus
       ACCESS          not-implemented
       DESCRIPTION     "Not supported"

       VARIATION       cLAPGroupsPolicyEntry
       ACCESS          not-implemented
       DESCRIPTION     "Not supported"

       VARIATION       cLAPGroupsPolicyWlanId
       ACCESS          not-implemented
       DESCRIPTION     "Not supported"

       VARIATION       cLAPGroupsPolicyPriIndex
       ACCESS          not-implemented
       DESCRIPTION     "Not supported"

       VARIATION       cLAPGroupsPolicyIndex
       ACCESS          not-implemented
       DESCRIPTION     "Not supported"

       VARIATION       cLAPGroupsPolicyWlanProfile
       ACCESS          not-implemented
       DESCRIPTION     "Not supported"

       VARIATION       cLAPGroupsPolicyRowStatus
       ACCESS          not-implemented
       DESCRIPTION     "Not supported"

       VARIATION       cLPolicyActiveHoursEntry
       ACCESS          not-implemented
       DESCRIPTION     "Not supported"

       VARIATION       cLPolicyActiveDay
       ACCESS          not-implemented
       DESCRIPTION     "Not supported"

       VARIATION       cLPolicyActiveStartTime
       ACCESS          not-implemented
       DESCRIPTION     "Not supported"

       VARIATION       cLPolicyActiveEndTime
       ACCESS          not-implemented
       DESCRIPTION     "Not supported"

       VARIATION       cLPolicyActiveHoursRowStatus
       ACCESS          not-implemented
       DESCRIPTION     "Not supported"

       VARIATION       cLAPGroupsMultipleVenueEntry
       ACCESS          not-implemented
       DESCRIPTION     "Not supported"

       VARIATION       cLAPGroupsMultipleVenueLanguage
       ACCESS          not-implemented
       DESCRIPTION     "Not supported"

       VARIATION       cLAPGroupsMultipleVenueName
       ACCESS          not-implemented
       DESCRIPTION     "Not supported"

       VARIATION       cLAPGroupsMultipleVenueRowStatus
       ACCESS          not-implemented
       DESCRIPTION     "Not supported"

       VARIATION       cLWlan11uRealmEntry
       ACCESS          not-implemented
       DESCRIPTION     "Not supported"

       VARIATION       cLWlan11uRealmIndex
       ACCESS          not-implemented
       DESCRIPTION     "Not supported"

       VARIATION       cLWlan11uRealmName
       ACCESS          not-implemented
       DESCRIPTION     "Not supported"

       VARIATION       cLWlan11uRealmRowStatus
       ACCESS          not-implemented
       DESCRIPTION     "Not supported"

       VARIATION       cLAPGroupsVlanConfigEntry
       ACCESS          not-implemented
       DESCRIPTION     "Not supported"

       VARIATION       cLAPGroupName
       ACCESS          not-implemented
       DESCRIPTION     "Not supported"

       VARIATION       cLAPGroupsVlanMappingInterfaceName
       ACCESS          not-implemented
       DESCRIPTION     "Not supported"

       VARIATION       cLAPGroupNACSupport
       ACCESS          not-implemented
       DESCRIPTION     "Not supported"

       VARIATION       cLAPGroupsVlanConfigRowStatus
       ACCESS          not-implemented
       DESCRIPTION     "Not supported"

       VARIATION       cLAPGroupsVlanConfigStorageType
       ACCESS          not-implemented
       DESCRIPTION     "Not supported"

       VARIATION       cLAPGroupsWlanOrderIndex
       ACCESS          not-implemented
       DESCRIPTION     "Not supported"

       VARIATION       cLAPGroupsVlanMappingInterfaceNameRev1
       ACCESS          not-implemented
       DESCRIPTION     "Not supported"

       VARIATION       cLWlan11uRealmEapAuthEntry
       ACCESS          not-implemented
       DESCRIPTION     "Not supported"

       VARIATION       cLWlan11uRealmEapAuthIndex
       ACCESS          not-implemented
       DESCRIPTION     "Not supported"

       VARIATION       cLWlan11uRealmEapAuthMethod
       ACCESS          not-implemented
       DESCRIPTION     "Not supported"

       VARIATION       cLWlan11uRealmEapAuthParam
       ACCESS          not-implemented
       DESCRIPTION     "Not supported"

       VARIATION       cLWlan11uRealmEapAuthCredentialType
       ACCESS          not-implemented
       DESCRIPTION     "Not supported"

       VARIATION       cLWlan11uRealmEapAuthRowStatus
       ACCESS          not-implemented
       DESCRIPTION     "Not supported"

       VARIATION       cLPolicyDeviceEntry
       ACCESS          not-implemented
       DESCRIPTION     "Not supported"

       VARIATION       cLPolicyDeviceIndex
       ACCESS          not-implemented
       DESCRIPTION     "Not supported"

       VARIATION       cLPolicyDeviceName
       ACCESS          not-implemented
       DESCRIPTION     "Not supported"

       VARIATION       cLPolicyDeviceRowStatus
       ACCESS          not-implemented
       DESCRIPTION     "Not supported"

       VARIATION       cLAPGroupsHyperlocationConfigEntry
       ACCESS          not-implemented
       DESCRIPTION     "Not supported"

       VARIATION       cLAPGroupsHyperlocationEnable
       ACCESS          not-implemented
       DESCRIPTION     "Not supported"

       VARIATION       cLAPGroupsPakRssiThreshold
       ACCESS          not-implemented
       DESCRIPTION     "Not supported"

       VARIATION       cLAPGroupsPakRssiThresholdTrigger
       ACCESS          not-implemented
       DESCRIPTION     "Not supported"

       VARIATION       cLAPGroupsPakRssiNtpIpAddressType
       ACCESS          not-implemented
       DESCRIPTION     "Not supported"

       VARIATION       cLAPGroupsPakRssiNtpAddress
       ACCESS          not-implemented
       DESCRIPTION     "Not supported"

   ::= { ciscoLwappWlanCapability 1 }

END
