-- *****************************************************************
-- ciscoMgx8800IfMappingCapability MIB
--
-- AGENT-CAPABILITIES mib for CISCO-MGX8800-IF-MAPPING-MIB
--
-- August 2002, Subra Hegde
--
-- Copyright(c) 2002 by Cisco Systems,Inc.
--
-- *****************************************************************

CISCO-MGX8800-IF-MAPPING-CAPABILITY DEFINITIONS ::= BEGIN

IMPORTS
        MODULE-IDENTITY, 
        Unsigned32
                FROM SNMPv2-SMI
        AGENT-CAPABILITIES
                FROM SNMPv2-CONF
        ciscoAgentCapability
                FROM CISCO-SMI;   

ciscoMgx8800IfMappingCapability MODULE-IDENTITY
        LAST-UPDATED    "200208010000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
        DESCRIPTION
            "The Agent Capabilities for 
            CISCO-MGX8800-IF-MAPPING-MIB.

            - The cmiMappingCapabilityMgxV3R00 is for 
              MGX8850 Release 3.0.00.

            - The cmiMappingCapabilityRpmxfV12R02 is for
              RPM-XF module."

        REVISION "200208010000Z"
        DESCRIPTION
            "Initial version of this MIB module."
        ::= { ciscoAgentCapability 278 }

cmiMappingCapabilityMgxV3R00 AGENT-CAPABILITIES

PRODUCT-RELEASE "MGX8850 Release 3.0.00"
STATUS          current
DESCRIPTION     "Agent capabilities for MGX8850."

SUPPORTS        CISCO-MGX8800-IF-MAPPING-MIB
INCLUDES        { cmimPhysToIfMIBGroup  }

VARIATION       cmimIfType 
SYNTAX          INTEGER {
                     physicalLine(1),
                     atm(3),
                     atmVirtual(4),
                     adjCardApsLine(6)
                }
DESCRIPTION     "AXSM-A/AXSM-B Support only subset of
                values."

VARIATION        cmimIfType 
SYNTAX           INTEGER {
                     physicalLine(1),
                     atmIma(2),
                     atm(3),
                     atmVirtual(4),
                     adjCardApsLine(6),
                     imaGrpAtmPhy(9)
                 }
DESCRIPTION      "AXSM-E, PXM1-E Support only subset of
                 values."

VARIATION        cmimIfType 
SYNTAX           INTEGER {
                     physicalLine(1),
                     atmVirtual(4)
                 }
DESCRIPTION     "FRSM12 support only subset of values."

VARIATION        cmimIfType 
SYNTAX           INTEGER {
                     physicalLine(1),
                     adjCardApsLine(6),
                     sonetVT(8),
                     srmBertLine(10),
                     srmBertPort(11)
                 }
DESCRIPTION      "SRM-E Support only subset of values."

VARIATION        cmimIfType 
SYNTAX           INTEGER {
                     physicalLine(1),
                     ds1Inds3(5),
                     srmBertLine(10),
                     srmBertPort(11)
                 }
DESCRIPTION      "SRM Support only subset of values."

VARIATION       cmimIfType 
SYNTAX          INTEGER {
                    atmVirtual(4)
                }
DESCRIPTION     "Narrow Band Service Modules(CESM, FRSM,AUSM etc)
                and RPM-PR support only subset of values."
::= { ciscoMgx8800IfMappingCapability 1 }

cmiMappingCapabilityRpmxfV12R02 AGENT-CAPABILITIES

PRODUCT-RELEASE      "IOS Release 12.2(8)T2."
STATUS               current
DESCRIPTION          "Agent capabilities for RPM-XF
module."

SUPPORTS        CISCO-MGX8800-IF-MAPPING-MIB
INCLUDES        { cmimPhysToIfMIBGroup  }

VARIATION       cmimIfNumber
SYNTAX          Unsigned32(1..2)
DESCRIPTION     "Value 1 is applicable for values of 
                cmimIfType: atmVirtual(4), propAtm(7).
                The range 1..2 is applicable
                for cmimIfType=physicalLine(1)."

VARIATION       cmimIfType 
SYNTAX          INTEGER {
                    physicalLine(1),
                    atmVirtual(4),
                    propAtm(7)
                }
DESCRIPTION    "Does not support other values.
               The value atmVirtual(4) is used for returning
               cmimIfIndex value of LIN Number reported
               to PNNI Controller(VSI Controller)."
::= { ciscoMgx8800IfMappingCapability 2 }

END
