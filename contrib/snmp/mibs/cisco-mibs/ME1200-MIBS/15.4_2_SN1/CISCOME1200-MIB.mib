-- *****************************************************************
-- CISCOME1200-MIB:  Root for Cisco ME1200
--   
-- Copyright (c) 2002-2013 Vitesse Semiconductor Corporation "Vitesse". 
-- All Rights Reserved.
--   
-- ****************************************************************

CISCOME1200-MIB DEFINITIONS ::= BEGIN

IMPORTS
    MODULE-IDENTITY,
    OBJECT-IDENTITY
        FROM SNMPv2-SMI
    ciscoMgmt
        FROM CISCO-SMI;

ciscoME1200MIB MODULE-IDENTITY
    LAST-UPDATED "201401280000Z"
    ORGANIZATION
        "Vitesse Semiconductor Corporation"
    CONTACT-INFO
        "Palle Christensen <pallec@vitesse.com>"
    DESCRIPTION
        "The collection of MIBs relating to Cisco ME1200"
    REVISION    "201401280000Z"
    DESCRIPTION
        "Initial version"
    ::= { ciscoMgmt 815 }

me1200SwitchMgmt OBJECT-IDENTITY
    STATUS          current
    DESCRIPTION
        "switchMgmt is the root OBJECT IDENTIFIER from
         which object id values are assigned."
    ::= { ciscoME1200MIB 1 }

END
