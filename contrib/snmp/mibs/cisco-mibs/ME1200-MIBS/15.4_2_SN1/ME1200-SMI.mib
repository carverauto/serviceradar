-- *****************************************************************
-- ME1200-SMI:  Vitesse enterprise structure 
--   
-- Copyright (c) 2002-2013 Vitesse Semiconductor Corporation "Vitesse". 
-- All Rights Reserved.
--   
-- ****************************************************************

ME1200-SMI DEFINITIONS ::= BEGIN

IMPORTS
    MODULE-IDENTITY,
    OBJECT-IDENTITY,
    enterprises
        FROM SNMPv2-SMI;


me1200 MODULE-IDENTITY
    LAST-UPDATED    "201309240000Z"
    ORGANIZATION    "Vitesse Semiconductor Corporation"
    CONTACT-INFO
            "Vitesse Semiconductor Corporation"
    DESCRIPTION
        "The Structure of Management Information for the
        Vitesse enterprise."
    REVISION        "201309240000Z"
    DESCRIPTION
        "Initial version of this MIB module."
    ::= { enterprises 9 }


me1200SwitchMgmt OBJECT-IDENTITY
    STATUS          current
    DESCRIPTION
        "switchMgmt is the root OBJECT IDENTIFIER from
         which object id values are assigned."
    ::= { me1200 1 }



END
